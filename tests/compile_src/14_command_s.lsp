(defun t23-make-circle (cx cy r)
  (command-s "_.CIRCLE" (list cx cy 0) r)
  (entlast))

(defun t23-created-circle-p ()
  (command-s "_.UNDO" "_BEGIN")
  (setq e (t23-make-circle 0 0 5))
  (setq d0 (if (and e (entget e)) (cdr (assoc 0 (entget e))) nil))
  (command-s "_.ERASE" e "")
  (command-s "_.UNDO" "_END")
  (if (= d0 "CIRCLE") T nil))
