;; Auto-decompiled from bib.fas
;; Generated AutoLISP output

(defun fas-polar1 (value)
  value
)

(defun fas-rtos1 (value)
  value
)

(defun fas-rtos3 (bucket key value)
  (if value value key)
)

(defun fas-assoc-value (data key / hit)
  (cond
    ((null data) nil)
    ((and (listp key) (= (car key) 'lambda)) (apply key (list data)))
    ((and (listp key) (not (null key))) (mapcar '(lambda (item) (fas-assoc-value data item)) key))
    ((and (numberp key) (= (type data) 'ENAME) (setq hit (assoc key (entget data)))) (cdr hit))
    ((and (listp data) (numberp key)) (nth key data))
    ((and (listp data) (listp (car data)) (setq hit (assoc key data))) (cdr hit))
    (T nil)
  )
)

(defun in_param (data key)
  (fas-assoc-value data key)
)

(defun fas-getvar2 (data key)
  (fas-assoc-value data key)
)

(defun fas-getvar3 (data key default / value)
  (setq value (fas-assoc-value data key))
  (if value value default)
)

(defun fas-1- (value)
  (if (numberp value) (1- value) value)
)

(defun axedyn-reaccreate (value)
  value
)

(defun *en_ray* (entity data)
  (if entity entity data)
)

(defun fas-select-entity (message / picked)
  (setq picked (entsel (if (= (type message) 'STR) message "\nSelect object: ")))
  (cond
    ((= (type picked) 'ENAME) picked)
    ((and (listp picked) picked) (car picked))
    (T nil)
  )
)

(defun projet_pa_projet_ar_projet (arg_1 arg_2 arg_3 arg_4 arg_5 arg_6 / picked)
  (setq picked (fas-select-entity arg_5))
  picked
)

(defun axedyn-list ()
  (axedyn-setrayext 'vl-position)
)

(defun axedyn-get (en_rayon)
  (re_courant 'vl-position en_rayon)
)

(defun axedyn-set (en_rayon arg_2)
  (fas-rtos3 'vl-position en_rayon arg_2)
)

(defun axedyn-pop (en_rayon / local_1 projet_pa_axes_re_rayon gvar_3374 pt_2 axedyn-set gvar_3385 aopora-fin axedyn-list ha_ent re_bulge ls_axe polybib_geom-bulge2radius st_ray st_ray2 gvar_3331 dcl-combobox-getcursel stylepoly-list dcl-control-gettext dcl-form-close upperleftx st_txt gvar_3345)
  (entdel 'projet_pa_axes_bt_rayon)
  (if (and gvar_3345 (dcl-grid-clear projet_pa_axes_gr_elements))
    (progn
      (setq projet_pa_axes_re_rayon gvar_3345)
    )
    (progn
      (setq projet_pa_axes_re_rayon (re_courant 'vl-position en_rayon))
    )
  )
  (setq gvar_3374 (in_param projet_pa_axes_re_rayon '(st_nom st_style)))
  (setq pt_2 (in_param projet_pa_axes_re_rayon 'projet_pa_axes_st_nom))
  (setq axedyn-set (in_param projet_pa_axes_re_rayon 'projet_pa_axes_st_style))
  (setq gvar_3385 (in_param projet_pa_axes_re_rayon 'st_desc))
  (setq aopora-fin (in_param projet_pa_axes_re_rayon 'stylepoly-fillcombo))
  (setq axedyn-list (re_tan (re_ray pt_2)))
  (setq ha_ent (re_ray2 axedyn-list))
  (setq axedyn-set (en_ent axedyn-list axedyn-set ha_ent))
  (setq re_bulge (in_param projet_pa_axes_re_rayon 'dcl-control-settext))
  (setq ls_axe (in_param projet_pa_axes_re_rayon 'dcl-form-show))
  (setq polybib_geom-bulge2radius (pt_proj ls_axe))
  (setq st_ray (es_ext (es_ext (groupbib-list 10 (axedyn-reaccreate gvar_3385)))))
  (setq st_ray2 0)
  (setq st_ray2 0)
  (setq local_1 (dcl-grid-addrow (st_ray2 axedyn-set) 2))
  (while (<= local_1 0)
    (setq local_1 (1- local_1))
    (setq gvar_3331 (dcl-grid-addrow (st_axeid st_ray2) axedyn-set))
    (setq dcl-combobox-getcursel (dcl-grid-addrow st_ray2 gvar_3385))
    (setq stylepoly-list (dcl-grid-addrow (st_axeid st_ray2) gvar_3385))
    (setq dcl-control-gettext (dcl-grid-addrow (st_syle 2 st_ray2) gvar_3385))
    (if (and (projet_pa_axes_st_desc gvar_3331 'ha_poly) (cadr (ld_axedyn dcl-combobox-getcursel dcl-control-gettext stylepoly-list)))
      (progn
        (setq dcl-form-close (st_axedynid dcl-combobox-getcursel stylepoly-list dcl-control-gettext gvar_3331))
        (if (and aopora-fin (dcl-grid-addrow (st_axeid st_ray2) aopora-fin) (setq upperleftx (re_ray (dcl-grid-addrow (st_axeid st_ray2) aopora-fin))) (fas-polar1 upperleftx))
          (progn
            (sssetfirst upperleftx dcl-form-close (es_ext (groupbib-list 62 256) (groupbib-list 8 'upperlefty)))
          )
          (progn
            (column (re_ray re_bulge) (es_ext upperleftx))
            (setq upperleftx (*en_ray* dcl-form-close (es_ext (groupbib-list 70 128) (groupbib-list 62 256) (groupbib-list 8 'upperlefty))))
            (setq aopora-fin (row (fas-1- upperleftx) (st_axeid st_ray2) aopora-fin))
          )
        )
      )
      (progn
        (setq stylepoly-list (dcl-grid-addrow (st_axeid st_ray2) gvar_3385))
        (setq dcl-form-close (es_ext (es_ext (groupbib-list 10 stylepoly-list))))
        (if (and (dcl-grid-addrow (st_axeid st_ray2) aopora-fin) (setq upperleftx (re_ray (dcl-grid-addrow (st_axeid st_ray2) aopora-fin))))
          (progn
            (column upperleftx)
            (setq aopora-fin (row nil (st_axeid st_ray2) aopora-fin))
          )
        )
      )
    )
    (setq st_ray (bo_active st_ray dcl-form-close))
    (setq st_ray2 (st_axeid st_ray2))
  )
  (setq st_ray (bo_active st_ray (es_ext (es_ext (groupbib-list 10 (fas-1- gvar_3385)) (groupbib-list 42 0)))))
  (if (and gvar_3374 (re_ray gvar_3374) (fas-polar1 (re_ray gvar_3374)))
    (progn
      (sssetfirst (re_ray gvar_3374) st_ray (st_rayon (es_ext (groupbib-list 62 256) (groupbib-list 70 128)) polybib_geom-bulge2radius))
    )
    (progn
      (setq st_txt (*en_ray* st_ray (st_rayon (es_ext (groupbib-list 62 256) (groupbib-list 70 128)) polybib_geom-bulge2radius)))
      (setq gvar_3374 (fas-1- st_txt))
      (setq projet_pa_axes_re_rayon (st_rayon projet_pa_axes_re_rayon '(st_nom st_style) gvar_3374))
    )
  )
  (dcl-forcedwgredraw (es_ext (dcl-forcedwgredraw (re_ray pt_2))))
  (setq projet_pa_axes_re_rayon (st_rayon projet_pa_axes_re_rayon 'stylepoly-fillcombo aopora-fin))
  (if (and gvar_3345 (dcl-grid-clear projet_pa_axes_gr_elements))
    (progn
      (setq gvar_3345 projet_pa_axes_re_rayon)
      (dcl-grid-getcurcell)
    )
    (progn
      (fas-rtos3 'vl-position en_rayon projet_pa_axes_re_rayon)
    )
  )
)

(defun axedyn-setrayext (va_abs / getreal re_y *st_errmsg*)
  (entdel 'va_ins)
  (setq getreal (axedyn-reaccreate va_abs))
  (setq re_y (re_x va_abs))
  (setq re_y (re_y getreal (re_x va_abs)))
  (setq *st_errmsg* (*st_errmsg* getreal re_y))
  (if (repdyn-getpoint (dcl-grid-addrow *st_errmsg* (ocbib-id2ref *st_errmsg*)) 'en_polybase)
    (progn
      (ocbib-id2ref *st_errmsg*)
    )
    (progn
      (st_axeid (ocbib-id2ref *st_errmsg*))
    )
  )
)

(defun c:projet_pa_axes_oninitialize (/ in_lon0 ls_axe)
  (entdel "\nLigne d'absicce non présente")
  (bo_lctbase gvar_3216 ls_axe)
  (bo_lctabs lctbib-getvtx in_lon0)
  (dcl-grid-getcurcell)
  (vlax-invoke gvar_3212 'getlwpolyline)
  (vlax-vla-object->ename vlax-vla-object->ename nil)
  (vlax-vla-object->ename ha_blkbase nil)
  (setq in_lon0 (en_polyabs gvar_3345 'ls_obj 'ls_ext1))
  (setq ls_axe (in_param gvar_3345 'dcl-form-show))
  (ls_som0)
)

(defun c:projet_pa_axes_bt_ok_onclicked (/ errbib-catchapply in_lon0 assoc gvar_3345 polybib-absproj re_abs1)
  (entdel 'ls_props2)
  (re_abs1 projet_pa_axes_gr_elements)
  (fas-rtos3 'vl-position re_abs1 polybib-absproj)
  (blkbib-blk_ins re_abs1)
  (setq errbib-catchapply (dcl-grid-addrow (ls_props2 gvar_3216) (polybib-lwvertices 'axedyn-reaccreate (ls_dist))))
  (setq in_lon0 (errbib-catchapply lctbib-getvtx))
  (setq assoc (errbib-catchapply gvar_3187))
  (setq gvar_3345 (st_rayon gvar_3345 'dcl-form-show errbib-catchapply))
  (setq gvar_3345 (st_rayon gvar_3345 'ls_obj in_lon0))
  (setq gvar_3345 (st_rayon gvar_3345 '*st_axedynid* assoc))
  (setq polybib-absproj gvar_3345)
  (setq re_abs1 gvar_3221)
  (ls_som0)
)

(defun c:projet_pa_axes_onclose (/ blkpoly-proj st_grouphandle)
  (st_grouphandle nil nil)
  (ls_som0)
)

(defun c:projet_pa_axes_gr_elements_onselchanged (/ eq netbib-purgeblock gvar_3176 gvar_3331 gvar_3175 aopora-fin axedyn-set vla-put-rotation substr)
  (entdel 're_abs0)
  (st_grouphandle nil nil)
  (setq gvar_3176 nil)
  (setq gvar_3331 'ha_poly)
  (setq gvar_3175 'ls_ext1)
  (setq aopora-fin (in_param gvar_3345 'stylepoly-fillcombo))
  (setq axedyn-set (in_param gvar_3345 'projet_pa_axes_st_style))
  (or (or (re_angle eq_2 0) (re_angle eq_2 (vla-get-name (st_ray2 axedyn-set)))) (st_blkbase eq_2 255))
  T
  (setq gvar_3331 (dcl-grid-addrow eq_2 axedyn-set))
  (and (setq vla-put-rotation (dcl-grid-addrow eq_2 aopora-fin)) (setq substr (re_ray vla-put-rotation)) (st_grouphandle nil (pt_ptp1 substr)) (setq gvar_3175 (eo_blkbase gvar_3331 2 3)) (setq gvar_3176 polybib-vtxjoin))
  (vlax-invoke gvar_3212 (geombib-raccordmax 'debug (dcl-control-setenabled (st_axeid eq_2))))
  (vlax-vla-object->ename vlax-vla-object->ename gvar_3176)
  (vlax-vla-object->ename ha_blkbase gvar_3176)
  (bo_lctabs vlax-vla-object->ename gvar_3175)
  (setq gvar_3175 'ls_ext1)
  (bo_visible)
)

(defun c:projet_pa_axes_bt_rayon_onclicked (/ axedyn-set ls_entsnew gvar_3169 ls_dists pt_ins gvar_3345)
  (entdel 'ss_curv)
  (blkbib-blk_ins gvar_3221)
  (ls_group projet_pa_detail gvar_3169 255)
  (bo_lctabs vlax-vla-object->ename ls_dists)
  (setq axedyn-set (in_param gvar_3345 'projet_pa_axes_st_style))
  (setq ls_entsnew (blkpoly-ls_entsnew projet_pa_detail))
  (setq gvar_3169 (axedyn-reaccreate ls_entsnew))
  (setq ls_dists (errbib-catchapply vlax-vla-object->ename))
  (setq pt_ins (groupbib-listobj ls_dists))
  (setq axedyn-set (row pt_ins gvar_3169 axedyn-set))
  (setq gvar_3345 (st_rayon gvar_3345 'projet_pa_axes_st_style axedyn-set))
  (ls_entnew vlax-vla-object->ename 0 255)
)

(defun c:projet_pa_axes_re_rayon_onsetfocus ()
  (ls_entnew vlax-vla-object->ename 0 255)
)

(defun blkpoly-list ()
  (axedyn-setrayext 'blkpoly-substprops)
)

(defun blkpoly-get (en_rayon)
  (re_courant 'blkpoly-substprops en_rayon)
)

(defun blkpoly-set (en_rayon / arg_2)
  (fas-rtos3 'blkpoly-substprops en_rayon arg_2)
)

(defun blkpoly-insdetail (in_lon0 / gvar_3419 gvar_3417 listbib-remove-i axedyn-get)
  (entdel 'in_lon)
  (if (cadr (ocbib-ename2id '(ha_group ha_group ld_axe ha_axe ha_group ls_som0 ls_ray ls_ent ls_som in_lon0 in_lon in_node) in_lon0))
    (progn
      T
      (and (setq gvar_3419 (geombib-raccordmax (cdr 'in_node) '= "st_type")) (setq gvar_3417 (geombib-raccordmax in_lon0 'st_flag)) (setq listbib-remove-i (listbib-remove-i gvar_3419 3 100 gvar_3417)) (setq axedyn-get (ld_poly (= (listbib-insert-i (cdr (listbib-remove-i))) 'axedyn-pop) (fas-rtos1 'aobib-popall) (geombib-raccordmax (es_poly listbib-remove-i) '(en_poly ha_poly ld_poly ha_axe ha_ext ls_ray ls_ent in_node re_courant st_txt) in_lon0 'st_flag) 'en_poly 'en_poly 'en_poly 'ha_poly)) (member axedyn-get))
    )
  )
  (if (ocbib-ename2id '(ha_group ha_group ld_axe ha_axe ha_group ls_som0 ls_ray ls_ent ls_som in_lon0 in_lon in_node) in_lon0)
    (progn
      polybib-vtxjoin
    )
    (progn
      nil
    )
  )
)

(defun blkpoly-substprops (polybib_geom-bulge2radius arg_2)
  (if (re_angle (in_param polybib_geom-bulge2radius "Appliquer") 'st_btn)
    (progn
      (setq polybib_geom-bulge2radius (st_rayon polybib_geom-bulge2radius "Appliquer" (in_param arg_2 "Repère")))
    )
  )
  polybib_geom-bulge2radius
)

(defun polybib-proj2poly (ls_propsdescs str repdyn-get / gvar_2983 gvar_3241 gvar_3388 gvar_3247 pt_ref gvar_3244 gvar_3242)
  (entdel "Repère ")
  (setq gvar_2983 (dcl-control-setvisible ls_propsdescs))
  (setq gvar_3241 (re_y ls_propsdescs str))
  (setq gvar_3388 (dcl-control-setvisible gvar_3079 gvar_3241))
  (if (or (ls_ext2 gvar_3388 'ha_poly '(ls_props pt_ref)) (ls_ext2 gvar_3388 gvar_2983 '(ls_props pt_ref)))
    (progn
      (setq gvar_3247 (fas-getvar2 ls_propsdescs gvar_3241))
      (setq pt_ref (pt_ref gvar_3241 str))
      (setq gvar_3244 (fas-getvar3 gvar_3241 (st_syle (repdyn-isrep gvar_3236 'repdyn-isrep) gvar_3247) pt_ref))
      (setq gvar_3242 (fas-getvar3 gvar_3241 (dcl-grid-addrow (repdyn-isrep gvar_3236 'repdyn-isrep) gvar_3247) pt_ref))
      (if (or (ls_ext2 (pt_ref str gvar_3244) 'ha_poly '(ls_props pt_ref)) (ls_ext2 (pt_ref str gvar_3242) 'ha_poly '(ls_props pt_ref)))
        (progn
          (setq gvar_3241 gvar_3241)
        )
        (progn
          (setq gvar_3241 nil)
        )
      )
    )
    (progn
      (setq gvar_3241 gvar_3241)
    )
  )
  gvar_3241
)

(defun pa_detail_grd_props_update (/ local_0 polybib_geom-bulge2radius ls_vtxsapprox palbib-fin polybib-approxarc)
  (entdel "0.01")
  (*en_ins* ls_somcurve)
  (setq polybib_geom-bulge2radius (in_param gvar_3345 'polybib-absatpoint))
  (setq ls_vtxsapprox polybib-approxarc)
  (setq local_0 polybib_geom-bulge2radius)
  (foreach palbib-fin local_0
    (eo_blkpop ls_somcurve (dcl-grid-addrow 1 palbib-fin) (eo_blkbase (dcl-grid-addrow 2 palbib-fin) 2 2) (dcl-grid-addrow 4 palbib-fin))
  )
  (setq polybib-approxarc ls_vtxsapprox)
)

(defun c:projet_pa_detail_grd_props_onselchanged (/ eq netbib-purgeblock polybib_geom-bulge2radius polybib-approxarc palbib-fin blkpoly-point polybib-subpolybisinv polybib-subpolyoffinv bo_invpoly)
  (entdel 'ls_vtxapprox)
  (setq polybib_geom-bulge2radius (in_param gvar_3345 'polybib-absatpoint))
  (if (st_blkbase eq_2 255)
    (progn
      (setq polybib-approxarc eq_2)
    )
  )
  (setq palbib-fin (dcl-grid-addrow polybib-approxarc polybib_geom-bulge2radius))
  (setq blkpoly-point (dcl-grid-addrow 2 palbib-fin))
  (setq polybib-subpolybisinv (dcl-grid-addrow 4 palbib-fin))
  (if (cadr polybib-subpolybisinv)
    (progn
      (setq polybib-subpolybisinv "Impossible d'insérer le bloc droit")
    )
  )
  (bo_invpoly1 ls_somcurves (laybib-newlay polybib-subpolybisinv (polybib-lwvertices 'axedyn-reaccreate vlax-curve-isclosed)))
  (if (setq polybib-subpolyoffinv (laybib-newlay (axedyn-reaccreate palbib-fin) (polybib-lwvertices 'eo_polyabs blkpoly-txt)))
    (progn
      (st_grouphandle nil (pt_ptp1 bo_invpoly))
      (setq bo_invpoly (axedyn-reaccreate (dcl-grid-addrow polybib-subpolyoffinv blkpoly-txt)))
    )
    (progn
      (st_grouphandle nil nil)
    )
  )
  (bo_lctabs polybib-subpolyper (eo_blkbase blkpoly-point 2 2))
  (vlax-vla-object->ename polybib-subpolyper polybib-vtxjoin)
  (vlax-vla-object->ename ls_somcurves polybib-vtxjoin)
  (vlax-vla-object->ename gvar_2882 polybib-vtxjoin)
  (en_hatch polybib-subpolyper)
  (ls_entnew polybib-subpolyper 0 255)
)

(defun c:projet_pa_detail_btn_reset_onclicked ()
  (dcl-listbox-getselecteditems re_yinv)
  (eo_hatch)
  (ls_som0)
)

(defun c:projet_pa_detail_onclose (/ blkpoly-proj st_grouphandle)
  (dcl-listbox-getselecteditems re_yinv)
  (eo_hatch)
)

(defun blkpoly-getparents (arg_1 / local_1 gvar_3094 polybib_geom-bulge2radius palbib-fin)
  (entdel "TrueColor")
  (setq gvar_3094 (es_ext (in_param arg_1 'va_point)))
  (if (re_abs2 (in_param arg_1 'getpoint))
    (progn
      (setq gvar_3094 (dcl-grid-setcurcell gvar_3094 (groupbib-list 're_abs2 (in_param arg_1 'getpoint))))
    )
  )
  (setq polybib_geom-bulge2radius (in_param arg_1 'polybib-absatpoint))
  (setq local_1 polybib_geom-bulge2radius)
  (foreach palbib-fin local_1
    (if (ls_ext2 '(re_x re_y pt_poly re_anglepoly re_angle) (dcl-grid-addrow 4 palbib-fin))
      (progn
        (setq gvar_3094 (dcl-grid-setcurcell gvar_3094 (groupbib-list 're_abs2 (dcl-grid-addrow 5 palbib-fin))))
      )
    )
  )
  gvar_3094
)

(defun c:projet_pa_detail_btn_save_onclicked (/ gvar_3094)
  (entdel "PatternAngle")
  (re_abs2 (groupbib-list 'blkpoly-substprops re_yinv) gvar_3094)
  (fas-rtos3 'blkpoly-substprops re_yinv gvar_3345)
  (re_abs1 gvar_3066)
  (setq gvar_3094 (hachbib-getloops gvar_3345))
  (ls_som0)
)

(defun blkpolymod-close (/ local_0 blkpoly-vtx bo_invpoly gvar_3345 blkpoly-txt blkbib-vlget_atts)
  (entdel 'ls_loops)
  (ls_outersproj)
  (dcl-combobox-setcursel 'ls_innersproj)
  (dcl-combobox-setcursel 'ls_outer)
  (setq local_0 blkbib-vlget_atts)
  (foreach blkpoly-vtx local_0
    T
    (and blkpoly-vtx (ls_inner blkpoly-vtx))
  )
  (dcl-combobox-setcursel "ls_inner")
  (dcl-combobox-setcursel blkpoly-txt)
  (setq local_0 blkpoly-txt)
  (foreach bo_invpoly local_0
    (member (dcl-forcedwgredraw (axedyn-reaccreate bo_invpoly)))
  )
  (>= (re_ray (in_param gvar_3345 " [Abscisse/Origine/Fin/Milieu 2 points/Décalage d'un point/Repère] :")) polybib-vtxjoin)
  (dcl-combobox-setcursel "PatternName")
  (eo_poly)
  (dcl-combobox-setcursel '(en_poly eo_poly ls_props ls_vtxs ls_som pt_0 ls_somcurve ls_somcurves re_bu ls_vtx0))
  (setq gvar_3345 nil)
  (setq blkpoly-txt nil)
  (setq blkbib-vlget_atts nil)
  (ls_som0)
)

(defun c:projet_pa_detail_ls_rep_onselchanged (/ eo_poly arg_2)
  (eo_poly)
)

(defun c:projet_pa_detail_btn_param_onclicked (/ polybib-subpolybisinv polybib_geom-bulge2radius palbib-fin gvar_3345)
  (entdel "ConstantWidth")
  (setq polybib-subpolybisinv (dcl-grid-addrow (ls_props2 ls_somcurves) (polybib-lwvertices 'axedyn-reaccreate vlax-curve-isclosed)))
  (setq polybib_geom-bulge2radius (in_param gvar_3345 'polybib-absatpoint))
  (setq palbib-fin (dcl-grid-addrow polybib-approxarc polybib_geom-bulge2radius))
  (or (or (or (re_angle polybib-subpolybisinv "Impossible d'insérer le bloc droit") (re_angle polybib-subpolybisinv 'blkpoly-poly)) (re_angle polybib-subpolybisinv '(re_x re_y pt_poly re_anglepoly re_angle))) polybib-vtxjoin)
  (setq palbib-fin nil)
  (setq palbib-fin (reverse palbib-fin gvar_3345))
  (setq palbib-fin (reverse palbib-fin gvar_3345))
  (setq palbib-fin (reverse palbib-fin gvar_3345))
  (if palbib-fin
    (progn
      (en_blk ls_somcurve polybib-approxarc 1 (eo_blkbase (dcl-grid-addrow 2 palbib-fin) 2 2))
      (en_blk ls_somcurve polybib-approxarc 2 (dcl-grid-addrow 4 palbib-fin))
      (eo_poly)
      (eo_hatch)
      (setq polybib_geom-bulge2radius (row palbib-fin polybib-approxarc polybib_geom-bulge2radius))
      (setq gvar_3345 (st_rayon gvar_3345 'polybib-absatpoint polybib_geom-bulge2radius))
      (dcl-listbox-getselecteditems re_yinv)
    )
    (progn
      nil
    )
  )
)

(defun blkpolydial-getlong (palbib-fin va_echelle / blkpoly-point)
  (entdel 'ls_rep)
  (setq blkpoly-point (dcl-grid-addrow 2 palbib-fin))
  (setq va_echelle (errbib-catchapply polybib-subpolyper))
  (if (re_angle va_echelle (eo_blkbase blkpoly-point 2 2))
    (progn
      (ls_som0 'ls_repblk)
      (setq palbib-fin nil)
    )
    (progn
      (setq palbib-fin (row (groupbib-listobj va_echelle) 2 palbib-fin))
      (setq palbib-fin (row "Impossible d'insérer le bloc droit" 4 palbib-fin))
    )
  )
  palbib-fin
)

(defun blkpolydial-modrefbouton (/ polybib-subpolybisinv polybib_geom-bulge2radius palbib-fin ls_paramwcs gvar_2849)
  (entdel 'ls_repblks)
  (setq polybib-subpolybisinv (dcl-grid-addrow (ls_props2 ls_somcurves) (polybib-lwvertices 'axedyn-reaccreate vlax-curve-isclosed)))
  (setq polybib_geom-bulge2radius (in_param gvar_3345 'polybib-absatpoint))
  (setq palbib-fin (dcl-grid-addrow polybib-approxarc polybib_geom-bulge2radius))
  (setq ls_paramwcs nil)
  (or (or (or (re_angle polybib-subpolybisinv "Impossible d'insérer le bloc droit") (re_angle polybib-subpolybisinv 'blkpoly-poly)) (re_angle polybib-subpolybisinv '(re_x re_y pt_poly re_anglepoly re_angle))) polybib-vtxjoin)
  (setq gvar_2849 'blkbib-isuniform)
  (if (and (re_angle "normal" (undobib-start (dcl-grid-addrow 5 palbib-fin))) (en_txt (dcl-grid-addrow 5 palbib-fin)))
    (progn
      (setq gvar_2849 (geombib-raccordmax 'en_txt (dcl-grid-addrow 5 palbib-fin)))
    )
    (progn
      (setq gvar_2849 'eo_txt)
    )
  )
  (if (re_angle 'es_ext (undobib-start (dcl-grid-addrow 5 palbib-fin)))
    (progn
      (setq gvar_2849 'pt_11)
    )
    (progn
      (setq gvar_2849 'eo_txt)
    )
  )
  (re_hauteur polybib-subpolyper ls_paramwcs)
  (vlax-invoke gvar_2882 gvar_2849)
  (setq gvar_2849 'blkbib-isuniform)
  (setq ls_paramwcs polybib-vtxjoin)
  (ls_som0)
)

(defun blkpolydial-getpoint (palbib-fin va_echelle / gvar_2840)
  (entdel '*ls_reps*)
  (if (setq gvar_2840 (st_visi 'ls_reps))
    (progn
      (setq palbib-fin (row (pt_ins11 gvar_2840 va_echelle) 2 palbib-fin))
      (setq palbib-fin (row 'blkpoly-poly 4 palbib-fin))
      (setq palbib-fin (row gvar_2840 5 palbib-fin))
    )
    (progn
      (setq palbib-fin nil)
    )
  )
  palbib-fin
)

(defun blkpolydial-getrep (palbib-fin va_echelle / en_rayon gvar_2840)
  (entdel "Distance1_X")
  (if (setq en_rayon (va_param "Position1 X"))
    (progn
      (setq gvar_2840 (axedyn-reaccreate (pt_ins11 en_rayon)))
      (setq palbib-fin (row (pt_ins11 gvar_2840 va_echelle) 2 palbib-fin))
      (setq palbib-fin (row '(re_x re_y pt_poly re_anglepoly re_angle) 4 palbib-fin))
      (setq palbib-fin (row en_rayon 5 palbib-fin))
    )
    (progn
      (setq palbib-fin nil)
    )
  )
  palbib-fin
)

(defun c:projet_pa_detail_txt_value_onsetfocus ()
  (ls_entnew polybib-subpolyper 0 255)
)

(defun c:projet_pa_detail_btn_preview_onclicked (/ pt_0 gvar_2833 gvar_3345 blkbib-getparententities)
  (entdel "Distance2_X")
  (dcl-combobox-setcursel "Position2 X")
  (setq pt_0 (vlax-curve-getpointatdist (in_param gvar_3345 "\nPoint de base :")))
  (if pt_0
    (progn
      (setq gvar_2833 (dcl-grid-addrow (ls_props2 ls_vtx) pt_0))
      (setq gvar_3345 (st_rayon gvar_3345 'max gvar_2833))
    )
  )
  (dcl-listbox-getselecteditems re_yinv)
  (setq blkbib-getparententities (errbib-catchapply polybib-proj2poly))
  (setq gvar_3345 (st_rayon gvar_3345 "Repère" blkbib-getparententities))
  (ls_som0)
)

(defun blkpoly-mod-paramupdate (/ local_0 blkpoly-vtx gvar_2917 st_dist bo_invpoly gvar_2824 bo_invpoly2 blkbib-vlget_atts)
  (dcl-combobox-setcursel 'ls_propsbase)
  (setq local_0 blkbib-vlget_atts)
  (foreach blkpoly-vtx local_0
    (ls_inner blkpoly-vtx)
  )
  (dcl-combobox-setcursel 'ls_params)
  (setq gvar_2917 (blkpoly-hach re_yinv))
  (setq local_0 blkpoly-txt)
  (foreach st_dist local_0
    (*ha_blkbase* (dcl-forcedwgredraw bo_invpoly) (rtos (dcl-grid-addrow 1 bo_invpoly2)))
    (st_layer (dcl-forcedwgredraw bo_invpoly) (dcl-grid-addrow 2 bo_invpoly2))
    (dcl-forcedwgredraw (es_ext (dcl-forcedwgredraw bo_invpoly)))
    (setq bo_invpoly (axedyn-reaccreate st_dist))
    (setq gvar_2824 (eo_polyabs st_dist))
    (setq bo_invpoly2 (in_param gvar_2917 gvar_2824))
  )
  (dcl-combobox-setcursel 'st_axe)
  (setq blkbib-vlget_atts (es_ext))
  (setq local_0 blkpoly-txt)
  (foreach st_dist local_0
    (setq bo_invpoly (axedyn-reaccreate st_dist))
    (setq blkbib-vlget_atts (dcl-grid-setcurcell blkbib-vlget_atts (re_off1 (dcl-forcedwgredraw bo_invpoly))))
  )
  (ls_som0)
)

(defun blkpoly-ls_entsnew (arg_1 / distance ls_visiname *ls_paramentxy* arg_5 *error* pt_ins re_angle0 re_angle en_blkdroit eo_blkdroit gr pt re_x re_y local_1 local_6 pa_detail_grd_props_update st_2 ordrebib-moveabove re_flipy re_base princl sin gvar_2787 gvar_2785 gvar_3094 aopora-fin polybib-subpolybisinv pt_abs pt_param polybib_geom-bulge2radius gvar_3137 vla-put-insertionpoint)
  (entdel 'blkpoly-getbasey)
  (setq pa_detail_grd_props_update (es_ext))
  (setq st_2 (st_1 (ls_sup (dcl-forcedwgredraw *ls_paramentxy*) '(ls_props ls_prop in_num))))
  (setq ordrebib-moveabove (eo_hach (in_param arg_5 "\nPoint de base :")))
  (if ordrebib-moveabove
    (progn
      (setq re_flipy (re_flipx (in_param arg_5 "\nPoint de base :")))
      (setq re_flipy (in_param re_flipy (in_param arg_5 'max)))
      (setq re_base (polybib-lwvertices '(ls_prop re_abs0 re_abs pt re_dist re_base re_angle re_x re_y) re_flipy))
    )
  )
  (setq princl polybib-vtxjoin)
  (setq distance (dcl-forcedwgredraw distance))
  (setq sin (dcl-grid-addrow 'en_poly (ls_visient 'repdyn-isrep (in_param arg_5 "\ndécalage :"))))
  (setq gvar_2787 (dcl-grid-addrow 'en_poly (ls_visient 'repdyn-isrep (in_param arg_5 're_decalage))))
  (if (re_ray (in_param arg_5 'dcl-control-settext))
    (progn
      (setq gvar_2785 (sin *ls_paramentxy* distance arg_5))
      (setq gvar_3094 (re_ang *ls_paramentxy*))
    )
  )
  (dcl-combobox-setcursel 'pt_int)
  (setq local_6 st_2)
  (foreach aopora-fin local_6
    (setq polybib-subpolybisinv (in_param aopora-fin 0))
    (setq pt_abs (in_param gvar_3094 (in_param aopora-fin 5)))
    (setq pt_param T)
    (and (and (and (and (and (or (cadr ordrebib-moveabove) (laybib-newlay pt_abs re_base)) (and princl (re_angle "Fin BlKPoly-XY2WCS" polybib-subpolybisinv) (setq pt_abs (in_param gvar_3094 (in_param aopora-fin 5))) (in_param gvar_2785 pt_abs))) (and princl (re_angle "Fin BlKPoly-XY2WCS" polybib-subpolybisinv))) (and princl (re_angle 'projet_pa_detail_btn_param polybib-subpolybisinv))) (and princl (re_angle 'dcl-control-setfocus polybib-subpolybisinv))) (and princl (re_angle 'blkpoly-mod-paramupdate polybib-subpolybisinv)))
    (setq polybib_geom-bulge2radius (pt_param arg_1 re_angle0 aopora-fin ls_visiname sin gvar_2787))
    (if polybib_geom-bulge2radius
      (progn
        (setq pa_detail_grd_props_update (dcl-grid-setcurcell pa_detail_grd_props_update (st_rayon (es_ext (groupbib-list 'st_type 'blkpoly-mod-paramupdate) (groupbib-list 're_value pt_param)) polybib_geom-bulge2radius)))
      )
      (progn
        (setq princl nil)
      )
    )
    (dcl-combobox-setcursel "BlkPoly-GetParentEntities")
    (setq polybib_geom-bulge2radius (id_group arg_1 re_angle0 aopora-fin ls_visiname sin gvar_2787))
    (if polybib_geom-bulge2radius
      (progn
        (setq pa_detail_grd_props_update (dcl-grid-setcurcell pa_detail_grd_props_update (es_ext (groupbib-list 'st_type 'dcl-control-setfocus) (groupbib-list 're_value pt_param) polybib_geom-bulge2radius)))
      )
      (progn
        (setq princl nil)
      )
    )
    (setq gvar_3137 (id_group (dcl-forcedwgredraw (in_param aopora-fin 255))))
    (setq polybib_geom-bulge2radius (poly-polyside arg_1 re_angle0 aopora-fin gvar_3137 ls_visiname sin gvar_2787))
    (if polybib_geom-bulge2radius
      (progn
        (setq pa_detail_grd_props_update (dcl-grid-setcurcell pa_detail_grd_props_update (st_rayon (es_ext (groupbib-list 'st_type 'projet_pa_detail_btn_param) (groupbib-list 're_value pt_param)) polybib_geom-bulge2radius)))
      )
      (progn
        (setq princl nil)
      )
    )
    (setq polybib_geom-bulge2radius (poly-polyside arg_1 re_angle0 aopora-fin ls_visiname sin gvar_2787))
    (if polybib_geom-bulge2radius
      (progn
        (setq pa_detail_grd_props_update (dcl-grid-setcurcell pa_detail_grd_props_update (es_ext (groupbib-list 'st_type 'in_pos) (groupbib-list 're_deltay pt_abs) (groupbib-list 're_value pt_param) (axedyn-reaccreate polybib_geom-bulge2radius) (re_x polybib_geom-bulge2radius))))
      )
      (progn
        (setq princl nil)
      )
    )
    (setq vla-put-insertionpoint (re_ray (in_param gvar_2785 pt_abs)))
    (setq polybib_geom-bulge2radius (poly-polyside arg_1 re_angle0 aopora-fin ls_visiname sin gvar_2787))
    (if polybib_geom-bulge2radius
      (progn
        (setq pa_detail_grd_props_update (dcl-grid-setcurcell pa_detail_grd_props_update (es_ext (groupbib-list 'st_type 'projet_pa_detail_txt_value) (groupbib-list '(st_type ls_props ls_prop) vla-put-insertionpoint) (axedyn-reaccreate polybib_geom-bulge2radius) (re_x polybib_geom-bulge2radius) (groupbib-list 're_value pt_param))))
      )
      (progn
        (setq princl nil)
      )
    )
  )
  (if princl
    (progn
      pa_detail_grd_props_update
    )
    (progn
      nil
    )
  )
)

(defun blkpoly-point (arg_1 blkpoly-get ls_visiname sin / *error* pt_ins re_angle0 re_angle en_blkdroit eo_blkdroit gr pt re_x re_y re_abs0 re_abs re_base pt_2 re_dist re_angle_2 re_x_2 re_y_2 local_1 local_5 gvar_2939 gvar_3159 gvar_3158 gvar_2767 gvar_2765)
  (entdel 're_deltax)
  (setq gvar_2939 'ha_poly)
  (setq gvar_3159 (st_syle ls_visiname (ls_visient sin (axedyn-reaccreate blkpoly-get))))
  (if (and (re_deltax re_angle0) (and (re_deltax gvar_3159 'ha_poly) (re_deltax gvar_3159 (repdyn-get re_angle0))))
    (progn
      (setq gvar_3159 (re_deltax re_angle0 gvar_3159))
      (setq gvar_3158 (ls_visient sin (re_x blkpoly-get)))
      (setq gvar_2767 (ls_param re_angle0 gvar_3159))
      (setq gvar_2767 (ls_blk arg_1 gvar_2767 nil))
      (if gvar_2767
        (progn
          (setq gvar_2765 (fas-getvar2 arg_1 gvar_2767))
          (setq blkpoly-get (fas-getvar3 gvar_2767 (st_syle (repdyn-isrep gvar_3236 'repdyn-isrep) gvar_2765) gvar_3158))
        )
      )
    )
  )
  blkpoly-get
)

(defun blkpoly-vtx (arg_1 dcl-form-close ls_visiname sin / *error* pt_ins re_angle0 re_angle en_blkdroit eo_blkdroit gr pt re_x re_y ls_prop re_abs0 re_abs re_base pt_2 re_dist re_angle_2 re_x_2 re_y_2 local_1 local_5 local_6 local_7 projet_md_repblk_cb_blk1 dcl-combobox-addlist projet_md_repblk_cb_blk2 ls_update gvar_2759_c:projet_md_repblk_oninitialize gvar_2767 projet_pa_detail_vueblocs1 gvar_2956 projet_md_repblk_bv_1 dcl-blockview-displayblock gvar_2755_c:projet_md_repblk_cb_blk1_onselchanged gvar_3244 gvar_3242 projet_md_repblk_bv_2 gvar_2753_c:projet_md_repblk_cb_blk2_onselchanged st_blk2 gvar_2749 st_msg)
  (entdel 'ls_blk)
  (setq projet_md_repblk_cb_blk1 (es_ext))
  (setq dcl-combobox-addlist (axedyn-reaccreate dcl-form-close))
  (setq projet_md_repblk_cb_blk2 (in_param dcl-combobox-addlist 10))
  (setq ls_update (ls_visient sin sin (in_param dcl-combobox-addlist 42)))
  (setq local_6 (eo_polyabs dcl-form-close))
  (foreach gvar_2759_c:projet_md_repblk_oninitialize local_6
    (setq projet_md_repblk_cb_blk1 (vl-acad-defun projet_md_repblk_cb_blk1))
    (setq gvar_2767 (in_param gvar_2759_c:projet_md_repblk_oninitialize 10))
    (setq projet_pa_detail_vueblocs1 (st_syle ls_visiname (ls_visient sin (axedyn-reaccreate projet_md_repblk_cb_blk2))))
    (setq gvar_2956 (st_syle ls_visiname (ls_visient sin (axedyn-reaccreate gvar_2767))))
    (setq projet_md_repblk_bv_1 nil)
    (setq dcl-blockview-displayblock nil)
    (if (and (and re_base (re_deltax re_angle0)) (and re_base (re_deltax projet_pa_detail_vueblocs1 'ha_poly) (re_deltax gvar_2956 'ha_poly) (re_deltax projet_pa_detail_vueblocs1 gvar_2983) (re_deltax gvar_2956 gvar_2983)))
      (progn
        (if (or (re_deltax projet_pa_detail_vueblocs1 'ha_poly) (re_deltax projet_pa_detail_vueblocs1 gvar_2983))
          (progn
            (setq projet_pa_detail_vueblocs1 (re_deltax re_angle0 projet_pa_detail_vueblocs1))
            (setq projet_md_repblk_bv_1 polybib-vtxjoin)
          )
        )
        (if (or (re_deltax gvar_2956 'ha_poly) (re_deltax gvar_2956 gvar_2983))
          (progn
            (setq gvar_2956 (re_deltax re_angle0 gvar_2956))
            (setq dcl-blockview-displayblock polybib-vtxjoin)
          )
        )
        (if (re_angle projet_md_repblk_bv_1 dcl-blockview-displayblock)
          (progn
            (setq gvar_2755_c:projet_md_repblk_cb_blk1_onselchanged nil)
          )
          (progn
            (setq gvar_2755_c:projet_md_repblk_cb_blk1_onselchanged polybib-vtxjoin)
          )
        )
        (setq gvar_3244 (*st_errmsg* arg_1 (ls_param re_angle0 projet_pa_detail_vueblocs1)))
        (setq gvar_3242 (*st_errmsg* arg_1 (ls_param re_angle0 gvar_2956)))
        (if (and gvar_2755_c:projet_md_repblk_cb_blk1_onselchanged (re_deltax projet_pa_detail_vueblocs1 gvar_2956))
          (progn
            (setq projet_md_repblk_bv_2 (ls_visient 255 sin (re_x projet_md_repblk_cb_blk2)))
            (setq gvar_2753_c:projet_md_repblk_cb_blk2_onselchanged (ls_visient 255 sin (re_x gvar_2767)))
          )
          (progn
            (setq projet_md_repblk_bv_2 (ls_visient sin (re_x projet_md_repblk_cb_blk2)))
            (setq gvar_2753_c:projet_md_repblk_cb_blk2_onselchanged (ls_visient sin (re_x gvar_2767)))
          )
        )
        (or (and (and (or (ls_ext2 (axedyn-reaccreate projet_md_repblk_cb_blk2) (axedyn-reaccreate gvar_2767) '(st_blk1 st_blk2 ls_blk st_msg bo_go)) (ls_ext2 projet_md_repblk_bv_2 gvar_2753_c:projet_md_repblk_cb_blk2_onselchanged '(st_blk1 st_blk2 ls_blk st_msg bo_go))) (and (odclbib-fillcombo ls_update 'ha_poly) (projet_pa_axes_st_desc projet_md_repblk_bv_2 gvar_2753_c:projet_md_repblk_cb_blk2_onselchanged))) (and (re_angle (ocbib-id2ref (*st_errmsg* arg_1 gvar_3244)) (ocbib-id2ref (*st_errmsg* arg_1 gvar_3242))) (re_angle 'ha_poly (in_param (dcl-grid-addrow (ocbib-id2ref (*st_errmsg* arg_1 gvar_3244)) (blkpoly-set (fas-polar1 arg_1))) 42)))) (projet_pa_axes_st_desc projet_md_repblk_bv_2 gvar_2753_c:projet_md_repblk_cb_blk2_onselchanged))
        (setq st_blk2 (st_blk1 (in_param dcl-combobox-addlist 10) (in_param gvar_2759_c:projet_md_repblk_oninitialize 10) (ls_visient ls_update sin sin) '(st_blk1 st_blk2 ls_blk st_msg bo_go)))
        (setq gvar_2749 (es_ext))
        (setq local_7 st_blk2)
        (foreach st_msg local_7
          (setq gvar_2749 (dcl-grid-setcurcell gvar_2749 (es_ext (groupbib-list 10 (st_msg arg_1 re_angle0 (st_rayon (in_param st_msg 10) (es_ext 'ha_poly)) ls_visiname sin sin)))))
        )
        (setq gvar_2749 (es_ext (es_ext (groupbib-list 10 (st_msg arg_1 re_angle0 projet_md_repblk_cb_blk2 ls_visiname sin sin)) (groupbib-list 40 'ha_poly) (groupbib-list 41 'ha_poly) (groupbib-list 42 ls_update)) (es_ext (groupbib-list 10 (st_msg arg_1 re_angle0 gvar_2767 ls_visiname sin sin)) (groupbib-list 40 'ha_poly) (groupbib-list 41 'ha_poly) (groupbib-list 42 'ha_poly))))
        (setq gvar_2749 (bo_go arg_1 gvar_3244 gvar_3242 (dcl-grid-addrow projet_md_repblk_bv_2) (dcl-grid-addrow gvar_2753_c:projet_md_repblk_cb_blk2_onselchanged) gvar_2755_c:projet_md_repblk_cb_blk1_onselchanged))
        (setq gvar_2749 (alert arg_1 gvar_3244 gvar_3242 (dcl-grid-addrow projet_md_repblk_bv_2) polybib-vtxjoin gvar_2755_c:projet_md_repblk_cb_blk1_onselchanged))
        (setq gvar_2749 (c:projet_md_repblk_bt_add_onclicked arg_1 gvar_3244 projet_md_repblk_bv_2 gvar_2753_c:projet_md_repblk_cb_blk2_onselchanged ls_update sin))
        (setq projet_md_repblk_cb_blk1 (st_rayon projet_md_repblk_cb_blk1 gvar_2749))
        (setq dcl-combobox-addlist gvar_2759_c:projet_md_repblk_oninitialize)
      )
      (progn
        (setq re_base nil)
      )
    )
    (setq ls_update (ls_visient (in_param gvar_2759_c:projet_md_repblk_oninitialize 42) sin sin))
    (setq projet_md_repblk_cb_blk2 gvar_2767)
  )
  projet_md_repblk_cb_blk1
)

(defun blkpoly-hach (arg_1 / aopora-fin ls_visiname sin *error* pt_ins re_angle0 re_angle en_blkdroit eo_blkdroit gr pt re_x re_y ls_prop re_abs0 re_abs re_base pt_2 re_dist re_angle_2 re_x_2 re_y_2 local_1 local_5 local_6 projet_md_repblk_gr_repblk gvar_2741_c:projet_md_repblk_gr_repblk_onselchanged polybib_geom-bulge2radius gvar_2939 gvar_2735 getfiled st_file filebib-readcsv gvar_2730_c:projet_md_repblk_bt_load_onclicked)
  (entdel '(ls_repblk))
  (setq re_base polybib-vtxjoin)
  (setq projet_md_repblk_gr_repblk (in_param aopora-fin 255))
  (setq gvar_2741_c:projet_md_repblk_gr_repblk_onselchanged (dcl-forcedwgredraw projet_md_repblk_gr_repblk))
  (setq polybib_geom-bulge2radius (es_ext (groupbib-list "Appliquer" (ls_sup gvar_2741_c:projet_md_repblk_gr_repblk_onselchanged "Appliquer")) (groupbib-list '(st_blk ls_repblk) (ls_sup gvar_2741_c:projet_md_repblk_gr_repblk_onselchanged '(st_blk ls_repblk))) (groupbib-list 'c:projet_md_repblk_bt_del_onclicked (ls_sup gvar_2741_c:projet_md_repblk_gr_repblk_onselchanged 'c:projet_md_repblk_bt_del_onclicked)) (groupbib-list '(st_file ls_reps ls_repblks) (ls_sup gvar_2741_c:projet_md_repblk_gr_repblk_onselchanged '(st_file ls_reps ls_repblks)))))
  (setq ls_prop (ls_sup gvar_2741_c:projet_md_repblk_gr_repblk_onselchanged "Choix du ficher"))
  (setq gvar_2939 (fas-getvar2 re_angle0 (ls_param re_angle0 ls_visiname)))
  (setq ls_prop (st_syle ls_prop gvar_2939))
  (setq gvar_2735 (getfiled projet_md_repblk_gr_repblk))
  (setq re_base polybib-vtxjoin)
  (setq getfiled (es_ext))
  (setq st_file (es_ext))
  (setq local_6 (axedyn-reaccreate gvar_2735))
  (foreach filebib-readcsv local_6
    (setq getfiled (dcl-grid-setcurcell getfiled (filebib-readcsv arg_1 re_angle0 filebib-readcsv ls_visiname sin sin)))
  )
  (setq local_6 (eo_polyabs gvar_2735))
  (foreach gvar_2730_c:projet_md_repblk_bt_load_onclicked local_6
    (if gvar_2730_c:projet_md_repblk_bt_load_onclicked
      (progn
        (setq st_file (dcl-grid-setcurcell st_file (filebib-readcsv arg_1 re_angle0 gvar_2730_c:projet_md_repblk_bt_load_onclicked ls_visiname sin sin)))
      )
    )
  )
  (if re_base
    (progn
      (es_ext (groupbib-list 'blkpolymod-close getfiled) (groupbib-list '(st_file ls_temp) st_file) (groupbib-list 'ld_detail (ls_sup gvar_2741_c:projet_md_repblk_gr_repblk_onselchanged '(lambda (ls_repblk) (list (car ls_repblk) (cdr ls_repblk))))) (groupbib-list '(ls_parents) (ls_sup gvar_2741_c:projet_md_repblk_gr_repblk_onselchanged 'ls_temp)) (groupbib-list '(ls_parents ls_props ls_prop) ls_prop) (groupbib-list 'blkpoly-getparents (ls_sup gvar_2741_c:projet_md_repblk_gr_repblk_onselchanged 'filebib-writecsv)) (groupbib-list 'polybib-absatpoint polybib_geom-bulge2radius))
    )
    (progn
      nil
    )
  )
)

(defun blkpoly-poly (arg_1 aopora-fin ls_visiname sin / *error* pt_ins re_angle0 re_angle en_blkdroit eo_blkdroit gr pt re_x re_y ls_prop re_abs0 re_abs re_base pt_2 re_dist re_angle_2 re_x_2 re_y_2 local_1 local_5 ls_propsdescs projet_md_repblk polybib_geom-bulge2radius dcl-form-close projet_md_repblk_cb_blk1 gvar_3385)
  (entdel 'c:projet_md_repblk_bt_save_onclicked)
  (setq ls_propsdescs (in_param aopora-fin 255))
  (setq projet_md_repblk (dcl-forcedwgredraw ls_propsdescs))
  (groupbib-list "Appliquer" (ls_sup projet_md_repblk "Appliquer"))
  (groupbib-list '(st_blk ls_repblk) (ls_sup projet_md_repblk '(st_blk ls_repblk)))
  (groupbib-list 'c:projet_md_repblk_bt_ok_onclicked (ls_sup projet_md_repblk 'c:projet_md_repblk_bt_ok_onclicked))
  (groupbib-list "Projet" (ls_sup projet_md_repblk "Projet"))
  'dcl-project-load
  (if (in_param aopora-fin 43)
    (progn
      (in_param aopora-fin 43)
    )
    (progn
      0
    )
  )
  (setq polybib_geom-bulge2radius (es_ext (groupbib-list) (groupbib-list 'c:projet_md_repblk_bt_del_onclicked (ls_sup projet_md_repblk 'c:projet_md_repblk_bt_del_onclicked)) (groupbib-list '(st_file ls_reps ls_repblks) (ls_sup projet_md_repblk '(st_file ls_reps ls_repblks))) (groupbib-list '(ss_blk ls_blk) (ls_sup projet_md_repblk '(ss_blk ls_blk)))))
  (setq dcl-form-close (blkpoly-set (fas-polar1 ls_propsdescs)))
  (setq projet_md_repblk_cb_blk1 (es_ext))
  (setq re_base polybib-vtxjoin)
  (if (re_angle ld_mod (ls_sup projet_md_repblk '(ss_blk ls_blk)))
    (progn
      (setq dcl-form-close (dcl-grid-setcurcell dcl-form-close (axedyn-reaccreate dcl-form-close)))
    )
  )
  (if (repdyn-getpoint sin 0)
    (progn
      (setq gvar_3385 (ssget gvar_3385))
    )
  )
  (setq projet_md_repblk_cb_blk1 (filebib-readcsv arg_1 re_angle0 dcl-form-close ls_visiname sin sin))
  (if re_base
    (progn
      (es_ext (groupbib-list 'blkpolydial-getrep projet_md_repblk_cb_blk1) (groupbib-list 'polybib-absatpoint polybib_geom-bulge2radius))
    )
    (progn
      nil
    )
  )
)

(defun blkpoly-blk (arg_1 aopora-fin arg_3 ls_visiname sin / *error* pt_ins re_angle0 re_angle en_blkdroit eo_blkdroit gr pt re_x re_y ls_prop re_abs0 re_abs re_base pt_2 re_dist re_angle_2 re_x_2 re_y_2 local_1 local_6 local_7 axedyn-get blkpoly-get dcl-listbox-clear blkbib-blkname gvar_2939 gvar_3011 va_fin bo_inv polybib_geom-bulge2radius gvar_3159 gvar_3158 gvar_2767 gvar_2765)
  (entdel 'ssget)
  (setq axedyn-get (dcl-forcedwgredraw (in_param aopora-fin 255)))
  (setq blkpoly-get (in_param aopora-fin 10))
  (setq dcl-listbox-clear (in_param aopora-fin 2))
  (setq blkbib-blkname (in_param aopora-fin 41))
  (setq gvar_2939 (in_param aopora-fin 50))
  (setq gvar_3011 nil)
  (setq local_7 gvar_2714)
  (foreach va_fin local_7
    (setq bo_inv (dcl-grid-setcurcell bo_inv (groupbib-list (axedyn-reaccreate va_fin) (eo_polyabs va_fin))))
    (setq bo_inv (dcl-grid-setcurcell bo_inv (groupbib-list (eo_polyabs va_fin) (axedyn-reaccreate va_fin))))
  )
  (or (and (and (and (and (and (re_angle sin 'en_poly) (re_angle sin '(va_point re_abs pt_base pt_1 pt_2 re_abs1 re_abs2))) (and (re_angle sin '(va_point re_abs pt_base pt_1 pt_2 re_abs1 re_abs2)) (ls_ext2 dcl-listbox-clear (in_param bo_inv dcl-listbox-clear)))) (and (re_angle sin 'en_poly) (re_angle sin '(va_point re_abs pt_base pt_1 pt_2 re_abs1 re_abs2)) (ls_ext2 dcl-listbox-clear (in_param bo_inv dcl-listbox-clear)))) (and (re_angle sin 'en_poly) (re_angle sin '(va_point re_abs pt_base pt_1 pt_2 re_abs1 re_abs2)) (in_param bo_inv dcl-listbox-clear))) (and (re_angle sin '(va_point re_abs pt_base pt_1 pt_2 re_abs1 re_abs2)) (re_angle sin 'en_poly) (in_param bo_inv dcl-listbox-clear))) (ls_inters dcl-listbox-clear))
  (setq gvar_2939 (st_syle gvar_3236 gvar_2939))
  (setq dcl-listbox-clear (in_param bo_inv dcl-listbox-clear))
  (setq dcl-listbox-clear (in_param bo_inv dcl-listbox-clear))
  (setq gvar_2939 (st_syle gvar_3236 gvar_2939))
  (setq dcl-listbox-clear (in_param bo_inv dcl-listbox-clear))
  (setq dcl-listbox-clear (in_param bo_inv dcl-listbox-clear))
  (dcl-combobox-setcursel '(in_id st_id ld_bord))
  (setq gvar_2939 gvar_2939)
  (dcl-combobox-setcursel "Bordure ")
  (setq gvar_2939 gvar_2939)
  (setq blkbib-blkname (es_ext (ls_visient sin (in_param aopora-fin 41)) (ls_visient sin (in_param aopora-fin 42)) 1))
  (setq polybib_geom-bulge2radius (es_ext (groupbib-list "Appliquer" (ls_sup axedyn-get "Appliquer")) (groupbib-list '(st_blk ls_repblk) (ls_sup axedyn-get '(st_blk ls_repblk))) (groupbib-list '(st_file ls_reps ls_repblks) (ls_sup axedyn-get '(st_file ls_reps ls_repblks)))))
  (setq gvar_3159 (st_syle (ls_visient sin (axedyn-reaccreate blkpoly-get)) ls_visiname))
  (if (and (re_deltax gvar_3159 'ha_poly) (re_deltax gvar_3159 (repdyn-get re_angle0)))
    (progn
      (setq gvar_3158 (ls_visient sin (re_x blkpoly-get)))
      (setq gvar_2767 (ls_param re_angle0 gvar_3159))
      (setq gvar_2767 (ls_blk arg_1 gvar_2767 nil))
      (if gvar_2767
        (progn
          (setq gvar_2765 (fas-getvar2 arg_1 gvar_2767))
          (setq ls_prop (st_syle gvar_2939 gvar_2765))
          (setq blkpoly-get (fas-getvar3 gvar_2767 (st_syle (repdyn-isrep gvar_3236 'repdyn-isrep) gvar_2765) gvar_3158))
          (setq gvar_3011 (es_ext (groupbib-list 'itemindexorcount dcl-listbox-clear) (groupbib-list 'eo_paramreact blkpoly-get) (groupbib-list 'value blkbib-blkname) (groupbib-list '(ls_parents ls_props ls_prop) ls_prop) (groupbib-list 'blkpolydial-modrefbouton arg_3) (groupbib-list 'polybib-absatpoint polybib_geom-bulge2radius)))
        )
      )
    )
  )
  gvar_3011
)

(defun blkpoly-txt (arg_1 aopora-fin ls_visiname sin / *error* pt_ins re_angle0 re_angle en_blkdroit eo_blkdroit gr pt re_x re_y ls_prop re_abs0 re_abs re_base pt_2 re_dist re_angle_2 re_x_2 re_y_2 local_1 local_5 local_6 gvar_2706 blkpoly-get gvar_2705 gvar_3255 gvar_2704 ssbib-ss2li gvar_3011 ld_bord polybib_geom-bulge2radius bordyn-getparents)
  (entdel "va_fin")
  (setq gvar_2706 (dcl-forcedwgredraw (in_param aopora-fin 255)))
  (setq blkpoly-get (in_param aopora-fin 10))
  (setq gvar_2705 (in_param aopora-fin 11))
  (setq gvar_3255 (in_param aopora-fin 1))
  (setq gvar_2704 (in_param aopora-fin 40))
  (setq ssbib-ss2li (es_ext))
  (setq gvar_3011 nil)
  (setq local_6 gvar_2703)
  (foreach ld_bord local_6
    (setq ssbib-ss2li (dcl-grid-setcurcell ssbib-ss2li (groupbib-list (axedyn-reaccreate ld_bord) (re_x ld_bord))))
    (setq ssbib-ss2li (dcl-grid-setcurcell ssbib-ss2li (groupbib-list (re_x ld_bord) (axedyn-reaccreate ld_bord))))
  )
  (setq polybib_geom-bulge2radius (es_ext (groupbib-list "Appliquer" (ls_sup gvar_2706 "Appliquer")) (groupbib-list '(st_blk ls_repblk) (ls_sup gvar_2706 '(st_blk ls_repblk))) (groupbib-list '(st_file ls_reps ls_repblks) (ls_sup gvar_2706 '(st_file ls_reps ls_repblks))) (groupbib-list 'bordyn-set (ls_sup gvar_2706 'bordyn-set))))
  (setq blkpoly-get (st_msg arg_1 re_angle0 blkpoly-get ls_visiname sin sin))
  (setq bordyn-getparents (st_msg arg_1 re_angle0 gvar_2705 ls_visiname sin sin))
  (setq gvar_3011 (es_ext (groupbib-list "Destruction des paramètres" gvar_3255) (groupbib-list 'eo_paramreact blkpoly-get) (groupbib-list "Destruction des variables" bordyn-getparents) (groupbib-list 'vlr-remove gvar_2704) (groupbib-list '(ls_parents ls_props ls_prop) ls_prop) (groupbib-list 'polybib-absatpoint polybib_geom-bulge2radius) (groupbib-list 71 (in_param aopora-fin 71)) (groupbib-list 72 (in_param aopora-fin 72)) (groupbib-list 73 (in_param aopora-fin 73))))
  gvar_3011
)

(defun blkpoly-lsparams ()
  (es_ext (es_ext '(ls_parents va_deb va_fin) 'blkpoly-poly 'en_poly 'ls_bordyn 're_rad) (es_ext 're_rayonmin 'blkpoly-poly 'en_poly 're_larg '(ls_bord a)) (es_ext '(lambda (a) (equal re_rad (car a) re_larg)) 'blkpoly-poly '(va_point re_abs pt_base pt_1 pt_2 re_abs1 re_abs2) 're_larg '(ls_bord a)) (es_ext 'vl-remove-if-not 'blkpoly-poly 'en_poly 'ls_bord '(inc ls_rads ls_vtx1 ls_vtx2 pt_1 pt_2 re_bulge re_rad)) (es_ext 'ls_rads 'blkpoly-poly '(va_point re_abs pt_base pt_1 pt_2 re_abs1 re_abs2) 'ls_bord '(inc ls_rads ls_vtx1 ls_vtx2 pt_1 pt_2 re_bulge re_rad)) (es_ext 'ls_vtx1 'ls_vtx2 'en_poly 'ls_bordyn 're_rad) (es_ext '(ls_abs inc ls_vtxsinters ls_vtxinters re_abs1 re_abs2) 'ls_vtx2 'en_poly 're_larg '(ls_bord a)) (es_ext 'poly-lspolyint 'ls_vtx2 'en_poly 'ls_bord '(inc ls_rads ls_vtx1 ls_vtx2 pt_1 pt_2 re_bulge re_rad)) (es_ext 'ls_abs 'ls_vtx2 '(va_point re_abs pt_base pt_1 pt_2 re_abs1 re_abs2) 'ls_bordyn 're_rad) (es_ext 'ls_vtxsinters 'ls_vtx2 '(va_point re_abs pt_base pt_1 pt_2 re_abs1 re_abs2) 're_larg '(ls_bord a)) (es_ext 'polybib-subvertices 'ls_vtx2 '(va_point re_abs pt_base pt_1 pt_2 re_abs1 re_abs2) 'ls_bord '(inc ls_rads ls_vtx1 ls_vtx2 pt_1 pt_2 re_bulge re_rad)))
)

(defun blkpoly-getbasey (re_dist arg_2 entlast polybib_geom-bulge2radius ocbib-id2ent arg_6 ls_style arg_8 arg_9 arg_10 / palbib-fin pt_ref gvar_2653 ls_prop)
  (entdel "-0.5")
  (setq palbib-fin (re_angle0 ocbib-id2ent polybib_geom-bulge2radius))
  (setq pt_ref (dcl-grid-addrow 2 palbib-fin))
  (setq gvar_2653 (re_x (dcl-grid-addrow 3 palbib-fin)))
  (setq pt_ref (st_syle gvar_2653 pt_ref))
  (setq pt_ref (ls_visient '(va_point re_abs pt_base pt_1 pt_2 re_abs1 re_abs2) arg_6 pt_ref arg_10))
  (setq ls_prop (st_syle 'ha_poly (ls_sup re_dist 'vlax-curve-getdistatparam)))
  (es_ext (groupbib-list ls_style 'ha_poly) (groupbib-list arg_8 pt_ref))
)

(defun blkpoly-getparententities (*ls_paramentxy* / distance arg_3 local_3 gvar_2785 re_bulge in_num ls_vtxsext pt_abs)
  (entdel 'ls_vtxsint)
  (dcl-combobox-setcursel "Impossible de générer les vertices du filaire externe")
  (setq gvar_2785 nil)
  (setq distance (dcl-forcedwgredraw distance))
  (setq re_bulge (in_param arg_3 'dcl-control-settext))
  (setq in_num (*in_num* (ls_sup (dcl-forcedwgredraw (re_ray re_bulge)) '(ls_props ls_prop in_num))))
  (setq local_3 in_num)
  (foreach ls_vtxsext local_3
    (setq pt_abs (re_courant ls_vtxsext 'blkpolydial-getlong))
    (if pt_abs
      (progn
        (dcl-grid-setcurcell gvar_2785 (groupbib-list (eo_polyabs pt_abs) (projet_pa_axes_ca_sommet ls_vtxsext)))
      )
      (progn
        gvar_2785
      )
    )
    (setq gvar_2785 nil)
  )
  (dcl-combobox-setcursel (es_ext "Impossible de générer le filaire central" gvar_2785))
  gvar_2785
)

(defun blkpoly-wcs2wxy (ls_vtxsbase arg_2 en_rayon / listbib-butlast distance gvar_3079 blkpoly-get polybib_geom-bulge2radius ls_visiname gvar_2828 gvar_2827 gvar_3241 gvar_2634 gvar_3388 en_polyint gvar_2822 palbib-fin blkpoly-point)
  (entdel "ZZZ-Filaire")
  (if gvar_3345
    (progn
      (setq listbib-butlast gvar_3345)
    )
    (progn
      (setq listbib-butlast (re_courant 'blkpoly-substprops en_rayon))
    )
  )
  (setq distance (re_ray (in_param listbib-butlast " [Abscisse/Origine/Fin/Milieu 2 points/Décalage d'un point/Repère] :")))
  (setq gvar_3079 (re_ray (hachbib-vtxs2hach (in_param listbib-butlast "Milieu"))))
  (setq blkpoly-get (in_param (fas-polar1 distance) 10))
  (setq polybib_geom-bulge2radius (in_param listbib-butlast 'polybib-absatpoint))
  (setq ls_visiname (dcl-control-setvisible gvar_3079 blkpoly-get))
  (if (re_angle (in_param listbib-butlast "\ndécalage :") 0)
    (progn
      'en_poly
    )
    (progn
      '(va_point re_abs pt_base pt_1 pt_2 re_abs1 re_abs2)
    )
  )
  (setq gvar_2828 nil)
  (if (re_angle (in_param listbib-butlast 're_decalage) 0)
    (progn
      'en_poly
    )
    (progn
      '(va_point re_abs pt_base pt_1 pt_2 re_abs1 re_abs2)
    )
  )
  (setq gvar_2827 nil)
  (setq gvar_3241 (re_y gvar_3079 ls_vtxsbase))
  (setq gvar_2634 (ls_visient 255 (poly-lwpoly_temp gvar_3079 ls_vtxsbase) (pt_ref ls_vtxsbase gvar_3241)))
  (setq gvar_3388 (dcl-control-setvisible gvar_3079 gvar_3241))
  (setq en_polyint (dcl-grid-addrow gvar_3388 ls_visiname))
  (setq gvar_2822 (in_param (re_angleins) arg_2))
  (setq palbib-fin (in_param polybib_geom-bulge2radius arg_2))
  (if (re_angle (axedyn-reaccreate gvar_2822) 'blkpoly-poly)
    (progn
      (setq blkpoly-point (ls_visient gvar_2828 (re_x gvar_2822) (dcl-grid-addrow en_polyint (axedyn-reaccreate (dcl-grid-addrow 2 palbib-fin)))))
      (setq blkpoly-point (re_deltax gvar_3079 blkpoly-point))
    )
    (progn
      (setq blkpoly-point (ls_visient gvar_2827 (re_x gvar_2822) (dcl-grid-addrow gvar_2634 (re_x (dcl-grid-addrow 2 palbib-fin)))))
    )
  )
  blkpoly-point
)

(defun bordyn-list ()
  (axedyn-setrayext 'chemdyn-get)
)

(defun bordyn-set (en_rayon arg_2)
  (fas-rtos3 'chemdyn-get en_rayon arg_2)
)

(defun bordyn-getparents (aopora-fin / gvar_3094 ls_inters1)
  (entdel 'ls_crois)
  (setq gvar_3094 (es_ext (in_param aopora-fin 'va_point)))
  (setq aopora-fin (in_param aopora-fin "Choisir un sommet"))
  (setq ls_inters1 (in_param aopora-fin 'croisdyn-getelems))
  (if (re_abs2 aopora-fin)
    (progn
      (setq gvar_3094 (dcl-grid-setcurcell gvar_3094 (groupbib-list 're_abs2 aopora-fin)))
    )
  )
  (if (re_abs2 ls_inters1)
    (progn
      (setq gvar_3094 (dcl-grid-setcurcell gvar_3094 (groupbib-list 're_abs2 ls_inters1)))
    )
  )
  gvar_3094
)

(defun bordyn-inters (ls_propsdescs / stylechem-get re_cotechem polybib_geom-bulge2radius 1- local_5 gvar_2544 gvar_2542 gvar_2471 in_num)
  (entdel 'ha_sup)
  (if (and (re_deltax ls_propsdescs) (cadr stylechem-get))
    (progn
      (setq polybib_geom-bulge2radius (dcl-grid-setcurcell polybib_geom-bulge2radius (groupbib-list 70 129)))
    )
    (progn
      (setq polybib_geom-bulge2radius (dcl-grid-setcurcell polybib_geom-bulge2radius (groupbib-list 70 128)))
    )
  )
  (setq gvar_2544 (bo_regen ls_propsdescs stylechem-get re_cotechem))
  (setq local_5 gvar_2544)
  nil
  (foreach gvar_2542 local_5
    (setq gvar_2471 (*en_ray* gvar_2542 polybib_geom-bulge2radius))
    (setq in_num (dcl-grid-setcurcell in_num gvar_2471))
  )
)

(defun c:projet_pa_bordyn_oninitialize (/ gvar_3345 in_lon0 gvar_2827 ls_axe polybib-subpolyoffinv)
  (entdel 'ha_pano)
  (bo_lctabs sivpano-set in_lon0)
  (ls_vtx0 sivpano-supportupdate (polybib-lwvertices 'ha_polyext (sivpano-supportupdate)))
  (setq gvar_3345 (re_courant "\n -> Panneau " re_yinv))
  (setq in_lon0 (in_param gvar_3345 'ls_obj))
  (setq gvar_2827 (in_param gvar_3345 'ls_croiselems))
  (setq ls_axe (in_param gvar_3345 'dcl-form-show))
  (if (setq polybib-subpolyoffinv (laybib-newlay ls_axe (polybib-lwvertices 'axedyn-reaccreate (sivpano-supportupdate))))
    (progn
      (bo_invpoly1 sivpano-supportupdate polybib-subpolyoffinv)
    )
    (progn
      (bo_invpoly1 sivpano-supportupdate 0)
    )
  )
  (ls_vtx0 aosup-sivpano (es_ext '(ls_axes ls_axe) "\n Vérification des axes..."))
  (if (re_angle gvar_2827 'en_poly)
    (progn
      (bo_invpoly1 aosup-sivpano 1)
    )
    (progn
      (bo_invpoly1 aosup-sivpano 0)
    )
  )
  (vlax-vla-object->ename ls_styles polybib-vtxjoin)
  (polybib-absrem)
)

(defun c:projet_pa_bordyn_bt_select_onclicked ()
  (entdel 'ls_fin)
  (axe-set 'ocbib-isok ls_styles)
)

(defun chemdyn-list ()
  (axedyn-setrayext " Incorrecte ! Effacement en cours...")
)

(defun chemdyn-get (en_rayon)
  (if (and (aosup-axe dcl-grid-clear) (dcl-grid-clear gvar_2442) gvar_3345 (ls_ext2 en_rayon (dcl-control-setenabled (in_param gvar_3345 'ls_axes))))
    (progn
      gvar_3345
    )
    (progn
      (re_courant " Incorrecte ! Effacement en cours..." en_rayon)
    )
  )
)

(defun chemdyn-pop (en_rayon / local_1 gvar_2437 in_num gvar_3155 gvar_2537 pt_pas chemdyn-hachtrace ls_inters1 gvar_2532 stylechem-get ls_deb gvar_2434 ls_axe re_cotechem gvar_2531 gvar_2530 re_bulge gvar_2519 gvar_2431 gvar_2429 aosup-mpolydyn polydyn-list ls_polydyns polydyn-set gvar_2418 sihlin-larg sihlin-trace projet_pa_chemdyn_bt_appliquer projet_pa_chemdyn_bt_ok gvar_2494 aoctrl-sihpp re_rayei re_rayie polybib-subpolybisinv gvar_2408 gvar_2827 gvar_2406 ld_crois croisdyn-getparents blkbib-getparententities listbib-min ls_bords reabib-deleteobjectreactor)
  (entdel 'ls_mpolydyn)
  (if gvar_3345
    (progn
      (setq gvar_2437 gvar_3345)
    )
    (progn
      (setq gvar_2437 (ls_deb en_rayon))
    )
  )
  (setq in_num (es_ext))
  (setq stylechem-get (in_param gvar_2437 'ocbib-isok))
  (setq ls_deb (es_ext))
  (setq gvar_2434 (in_param gvar_2437 'ls_croiselems))
  (setq ls_axe (in_param gvar_2437 'dcl-form-show))
  (setq stylechem-get (in_param gvar_2437 'ocbib-isok))
  (setq re_cotechem (in_param gvar_2437 'va_inters))
  (setq gvar_2531 (in_param gvar_2437 'parentbib-getson))
  (setq gvar_2530 (in_param gvar_2437 'ls_childs))
  (setq re_bulge (in_param gvar_2437 'dcl-control-settext))
  (setq gvar_2519 (va_ent (in_param gvar_2437 'dcl-form-show)))
  (setq gvar_2431 (in_param gvar_2519 'mpolydyn-set))
  (setq local_1 stylechem-get)
  (and (setq gvar_3155 'chemdyn-bordtrace) (setq gvar_2537 (chemdyn-bordtrace (in_param gvar_2437 'va_point))) (setq gvar_3155 "re_offset2") (setq pt_pas (in_param gvar_2437 "Choisir un sommet")) (setq chemdyn-hachtrace (re_offset2 pt_pas gvar_2537)) (setq gvar_3155 'chemdyn-polytrace) (setq ls_inters1 (in_param gvar_2437 'croisdyn-getelems)) (setq gvar_2532 (re_offset2 ls_inters1 gvar_2537)) (setq gvar_2429 (mpolydyn-popgo (in_param gvar_2437 'dcl-form-show))))
  (foreach aosup-mpolydyn local_1
    (if (cadr (aosup-mpolydyn aosup-mpolydyn))
      (progn
        (setq stylechem-get (blkpolydial-getpoint aosup-mpolydyn stylechem-get))
      )
    )
  )
  (setq polydyn-list (polydyn-list (groupbib-list " Incorrecte ! Effacement en cours..." en_rayon)))
  (setq local_1 polydyn-list)
  (foreach ls_polydyns local_1
    nil
    (or (or (and (odclbib-fillcombo (axedyn-reaccreate ls_polydyns) 'ls_polydyn) (setq polydyn-set (ls_polydyn (eo_polyabs ls_polydyns)))) (odclbib-fillcombo en_rayon (eo_polyabs (in_param polydyn-set "Origine")))) (odclbib-fillcombo en_rayon (eo_polyabs (in_param polydyn-set "\n -> PolyDyn "))))
    (setq ls_deb (dcl-grid-setcurcell ls_deb ls_polydyns))
    T
    (setq stylechem-get (dcl-grid-setcurcell stylechem-get ls_polydyns))
  )
  (setq gvar_2531 (in_param gvar_2437 'parentbib-getson))
  (setq gvar_2530 (in_param gvar_2437 'ls_childs))
  (setq gvar_2418 (polydyn-popgo gvar_2431))
  (setq sihlin-larg (aosup-polydyn gvar_2418))
  (setq sihlin-trace (projet_pa_croisdyn gvar_2418))
  (setq projet_pa_chemdyn_bt_appliquer (stylechem-list gvar_2537 chemdyn-hachtrace gvar_2532 sihlin-larg polybib-vtxjoin))
  (setq projet_pa_chemdyn_bt_ok (stylechem-list gvar_2537 chemdyn-hachtrace gvar_2532 sihlin-trace polybib-vtxjoin))
  (if (setq gvar_2494 (en_refoffset gvar_2531))
    (progn
      (sssetfirst gvar_2494 projet_pa_chemdyn_bt_appliquer (es_ext (groupbib-list 62 256) (groupbib-list 8 'en_edit)))
    )
    (progn
      (setq gvar_2494 (*en_ray* projet_pa_chemdyn_bt_appliquer (es_ext (groupbib-list 62 256) (groupbib-list 8 'en_edit))))
      (setq gvar_2494 (undobib-stop))
      (setq gvar_2437 (st_rayon gvar_2437 'parentbib-getson (fas-1- gvar_2494)))
    )
  )
  (aoctrl-polydyn (es_ext (dcl-forcedwgredraw gvar_2494)))
  (setq in_num (dcl-grid-setcurcell in_num gvar_2494))
  (setq gvar_3155 'aoctrl-mpolydyn)
  (if (setq aoctrl-sihpp (en_refoffset gvar_2530))
    (progn
      (sssetfirst aoctrl-sihpp projet_pa_chemdyn_bt_ok (es_ext (groupbib-list 62 256) (groupbib-list 8 'en_edit)))
    )
    (progn
      (setq aoctrl-sihpp (*en_ray* projet_pa_chemdyn_bt_ok (es_ext (groupbib-list 62 256) (groupbib-list 8 'en_edit))))
      (setq gvar_2437 (st_rayon gvar_2437 'ls_childs (fas-1- aoctrl-sihpp)))
    )
  )
  (aoctrl-polydyn (es_ext (dcl-forcedwgredraw aoctrl-sihpp)))
  (setq in_num (dcl-grid-setcurcell in_num aoctrl-sihpp))
  (setq local_1 (st_rayon stylechem-get ls_deb))
  (foreach aosup-mpolydyn local_1
    T
    (and (odclbib-fillcombo (undobib-start aosup-mpolydyn) 'es_ext) (odclbib-fillcombo (axedyn-reaccreate aosup-mpolydyn) 'ls_polydyn) (ls_polydyn (eo_polyabs aosup-mpolydyn)) (re_rayee (eo_polyabs aosup-mpolydyn)))
  )
  (setq local_1 gvar_2431)
  (foreach re_rayei local_1
    (setq re_rayie nil)
    (setq polybib-subpolybisinv (in_param re_rayei 'st_type))
    (or (or (or (odclbib-fillcombo polybib-subpolybisinv 're_rayii) (odclbib-fillcombo polybib-subpolybisinv '(st_id ld_crois))) (odclbib-fillcombo polybib-subpolybisinv "Croisée ")) (odclbib-fillcombo polybib-subpolybisinv "TEXTE"))
    (croisdyn-getparents gvar_2537 chemdyn-hachtrace gvar_2532 gvar_2408 gvar_2827 re_cotechem gvar_2406 ld_crois croisdyn-getparents stylechem-get blkbib-getparententities)
    (setq gvar_2408 (ls_visient gvar_2434 (in_param re_rayei "re_rayee")))
    (setq gvar_2827 (ls_visient gvar_2434 (in_param re_rayei 'ls_croiselems)))
    (setq gvar_2406 (in_param re_rayei "re_rayie"))
    (setq ld_crois (in_param re_rayei "ha_contour"))
    (setq croisdyn-getparents (in_param re_rayei 'croisdyn-set))
    (setq blkbib-getparententities (in_param re_rayei "Repère"))
    (setq ls_axe (in_param re_rayei 'dcl-form-show))
    (setq gvar_2408 (ls_visient gvar_2434 (in_param re_rayei "re_rayee")))
    (setq gvar_2827 (ls_visient gvar_2434 (in_param re_rayei 'ls_croiselems)))
    (setq ls_axe (in_param re_rayei 'dcl-form-show))
    (setq gvar_2519 (ls_vtxsbase2 ls_axe))
    (setq listbib-min (in_param gvar_2519 'intersbib-getinsidevtxs))
    (or (or (ls_ext2 re_rayei (vl-acad-defun (dcl-grid-addrow 1 gvar_2429))) (ls_ext2 re_rayei (vl-acad-defun (dcl-grid-addrow 2 gvar_2429)))) polybib-vtxjoin)
    (st_syleid gvar_2537 chemdyn-hachtrace gvar_2532 gvar_2408 gvar_2827 re_cotechem stylechem-get ls_axe)
    (setq re_rayie nil)
    (st_syleid gvar_2537 chemdyn-hachtrace gvar_2532 gvar_2408 gvar_2827 re_cotechem (st_rayon stylechem-get ls_deb) ls_axe)
    (setq re_rayie '(ls_style ls_elems ls_elem ls_hach ls_bords ls_bordi ls_borde))
    (st_syleid gvar_2537 chemdyn-hachtrace gvar_2532 gvar_2408 gvar_2827 re_cotechem (st_rayon stylechem-get ls_deb) ls_axe)
    (setq re_rayie '(lambda (ls_elem) (= "H" (listbib-key ls_elem "st_type"))))
    (setq gvar_2408 (st_syle gvar_2408 (ls_visient gvar_2827 listbib-min)))
    (listbib-sortkey gvar_2537 chemdyn-hachtrace gvar_2532 gvar_2408 ls_bords re_cotechem stylechem-get blkbib-getparententities)
    (setq gvar_2408 (ls_visient gvar_2434 (in_param re_rayei "re_rayee")))
    (setq gvar_2418 (dcl-grid-setcurcell gvar_2418 gvar_2408))
    (setq ls_bords (ls_visient gvar_2434 (in_param re_rayei '(lambda (ls_elem) (= "B" (listbib-key ls_elem "st_type"))))))
    (setq blkbib-getparententities (in_param re_rayei "Repère"))
    (ls_bordi gvar_2537 chemdyn-hachtrace gvar_2532 gvar_2408 re_cotechem stylechem-get blkbib-getparententities)
    (setq gvar_2408 (ls_visient gvar_2434 (in_param re_rayei "re_rayee")))
    (setq blkbib-getparententities (in_param re_rayei "Repère"))
  )
  (if (en_refoffset re_bulge)
    (progn
      (re_finoffset (re_ray re_bulge) (es_ext aoctrl-sihpp gvar_2494))
      (entbib-dellist re_bulge)
      (setq gvar_3155 're_deboffset)
      (column (re_ray re_bulge) in_num)
    )
    (progn
      (setq gvar_3155 '(ls_vtxsbase ls_vtxsbase2 en_poly ls_vtxs ls_polyhach ls_vtx en_hach))
      (setq reabib-deleteobjectreactor (polybib-inv in_num))
      (setq gvar_2437 (st_rayon gvar_2437 'dcl-control-settext (projet_pa_axes_ca_sommet reabib-deleteobjectreactor)))
      (mpolydyn-list en_rayon gvar_2437)
    )
  )
  T
  (ls_som0)
  (and (dcl-forcedwgredraw (es_ext (dcl-forcedwgredraw gvar_2537))) (setq gvar_3155 nil))
)

(defun chemdyn-bordtrace (arg_1 chemdyn-hachtrace arg_3 arg_4 re_cotechem stylechem-get ls_axe / st_type re_offset re_offset2 re_cote re_larg local_2 gvar_3155 dcl-form-close en_base entbib-key ha_contour en_refoffset)
  (entdel 'ls_borde)
  (setq gvar_3155 '(ld_crois ls_group ha_group))
  (setq dcl-form-close (stylechem-list arg_1 chemdyn-hachtrace chemdyn-hachtrace arg_3 polybib-vtxjoin))
  (setq gvar_3155 'ls_abs2)
  (setq en_base (*en_ray* dcl-form-close (es_ext (groupbib-list 8 'en_edit))))
  (setq gvar_3155 'eo_base)
  (setq entbib-key (palbib-init en_base (ls_param arg_1 chemdyn-hachtrace)))
  (setq ha_contour (palbib-init en_base (ls_param arg_1 chemdyn-hachtrace)))
  (setq en_refoffset (en_refoffset en_base entbib-key ha_contour arg_4 nil nil re_cotechem stylechem-get ls_axe))
  (en_ref1 (st_rayon en_refoffset (es_ext en_base)))
)

(defun chemdyn-hachtrace (arg_1 chemdyn-hachtrace arg_3 ls_bords re_cotechem stylechem-get blkbib-getparententities / st_type re_offset re_offset2 re_cote re_larg local_2 local_8 gvar_3155 projet_pa_chemdyn_re_cote ha_int1 ls_propsdescs dcl-form-close ha_ext2 gvar_2759_c:projet_md_repblk_oninitialize in_num gvar_2991 ls_elems1)
  (entdel 'en_ref2)
  (column ls_propsdescs)
  (setq gvar_3155 'ls_chem1)
  (setq projet_pa_chemdyn_re_cote (stylechem-list arg_1 chemdyn-hachtrace chemdyn-hachtrace arg_3 polybib-vtxjoin))
  (setq ha_int1 (ls_chem2 (stylechem-list arg_1 chemdyn-hachtrace chemdyn-hachtrace ls_bords polybib-vtxjoin)))
  (setq projet_pa_chemdyn_re_cote (st_rayon (vl-acad-defun projet_pa_chemdyn_re_cote) (es_ext (es_ext (re_angle0 10 (fas-1- projet_pa_chemdyn_re_cote)) (groupbib-list 40 'ha_poly) (groupbib-list 41 'ha_poly) (groupbib-list 42 'ha_poly))) ha_int1))
  (setq gvar_3155 'ha_int2)
  (setq ls_propsdescs (chemdyn-pop projet_pa_chemdyn_re_cote (es_ext (groupbib-list 70 1) (groupbib-list 8 blkbib-getparententities))))
  (setq dcl-form-close (ha_ext1 ls_propsdescs stylechem-get re_cotechem))
  (setq ha_ext2 (es_ext))
  (setq gvar_3155 'en_int1)
  (setq local_8 dcl-form-close)
  (foreach gvar_2759_c:projet_md_repblk_oninitialize local_8
    (setq ls_propsdescs (*en_ray* gvar_2759_c:projet_md_repblk_oninitialize (es_ext (groupbib-list 70 1) (groupbib-list 62 256) (groupbib-list "Appliquer" blkbib-getparententities))))
    (setq ha_ext2 (dcl-grid-setcurcell ha_ext2 ls_propsdescs))
    (setq in_num (dcl-grid-setcurcell in_num ls_propsdescs))
  )
  (setq gvar_3155 'en_int2)
  T
  (and (setq gvar_2991 (en_ext2 ha_ext2 nil 'en_ext1 'ha_poly 'en_poly nil (es_ext (groupbib-list 62 256) (groupbib-list "Appliquer" blkbib-getparententities)))) (setq ls_elems1 (rem gvar_2991)) (setq in_num (dcl-grid-setcurcell in_num ls_elems1)))
)

(defun chemdyn-polytrace (arg_1 chemdyn-hachtrace arg_3 re_cotechem stylechem-get blkbib-getparententities / st_type re_offset re_offset2 re_cote re_larg local_2 local_7 projet_pa_chemdyn_re_cote gvar_3153 gvar_2544 re_cote1 ls_propsdescs in_num)
  (entdel 'ls_elems2)
  (setq projet_pa_chemdyn_re_cote (stylechem-list arg_1 chemdyn-hachtrace chemdyn-hachtrace arg_3 polybib-vtxjoin))
  (setq gvar_3153 (chemdyn-pop projet_pa_chemdyn_re_cote (es_ext (groupbib-list 8 'en_edit))))
  (setq gvar_2544 (bo_regen gvar_3153 stylechem-get re_cotechem))
  (setq local_7 gvar_2544)
  (foreach re_cote1 local_7
    (setq ls_propsdescs (*en_ray* re_cote1 (es_ext (groupbib-list 62 256) (groupbib-list 8 blkbib-getparententities))))
    (setq in_num (dcl-grid-setcurcell in_num ls_propsdescs))
  )
  (column gvar_3153)
)

(defun chemdyn-signatrace (arg_1 / chemdyn-hachtrace arg_3 arg_4 re_cotechem arg_6 ld_crois croisdyn-getparents stylechem-get blkbib-getparententities st_type re_offset re_offset2 re_cote re_larg local_2 local_11 listbib-min projet_pa_chemdyn_re_cote gvar_3153 gvar_2544 re_cote1)
  (entdel 'ls_elems2)
  (column gvar_3153)
  (setq listbib-min (entbib-offsettemp (es_ext (groupbib-list "re_rayie" arg_6) (groupbib-list 'croisdyn-set croisdyn-getparents))))
  (setq projet_pa_chemdyn_re_cote (stylechem-list arg_1 chemdyn-hachtrace chemdyn-hachtrace arg_3 polybib-vtxjoin))
  (setq gvar_3153 (chemdyn-pop projet_pa_chemdyn_re_cote (es_ext (groupbib-list 8 'en_edit))))
  (setq gvar_2544 (bo_regen gvar_3153 stylechem-get re_cotechem))
  (setq local_11 gvar_2544)
  nil
  (foreach re_cote1 local_11
    (en_int1dc gvar_3153 'ha_poly (repdyn-get gvar_3153) 0 arg_4 ld_crois listbib-min blkbib-getparententities)
    (setq gvar_3153 (*en_ray* re_cote1 (es_ext (groupbib-list 8 blkbib-getparententities))))
    (column gvar_3153)
  )
)

(defun c:projet_pa_chemdyn_oninitialize (/ gvar_3345 in_lon0 gvar_2827 ls_axe polybib-subpolyoffinv)
  (entdel 'ha_pano)
  (bo_lctabs sivpano-set in_lon0)
  (ls_vtx0 en_ext1dc (polybib-lwvertices 'en_int2dc (en_ext2dc)))
  (setq gvar_3345 (ls_deb re_yinv))
  (setq in_lon0 (in_param gvar_3345 'ls_obj))
  (setq gvar_2827 (in_param gvar_3345 'ls_croiselems))
  (setq ls_axe (in_param gvar_3345 'dcl-form-show))
  (if (setq polybib-subpolyoffinv (laybib-newlay ls_axe (polybib-lwvertices 'axedyn-reaccreate (en_ext2dc))))
    (progn
      (bo_invpoly1 en_ext1dc polybib-subpolyoffinv)
    )
    (progn
      (bo_invpoly1 en_ext1dc 0)
    )
  )
  (ls_vtx0 ls_pt1 (es_ext '(ls_axes ls_axe) "\n Vérification des axes..."))
  (if (re_angle gvar_2827 'en_poly)
    (progn
      (bo_invpoly1 ls_pt1 1)
    )
    (progn
      (bo_invpoly1 ls_pt1 0)
    )
  )
  (vlax-vla-object->ename ls_dcs polybib-vtxjoin)
  (polybib-absrem)
)

(defun c:projet_pa_chemdyn_bt_select_onclicked (/ local_0 ls_abs1e gvar_2358)
  (entdel 'ls_fin)
  (setq ls_abs1e (es_ext en_ext1dc ls_pt1 gvar_2362 croisdyn-tracedemiext ls_pt1e ls_dcs))
  (setq local_0 ls_abs1e)
  (foreach gvar_2358 local_0
    (vlax-vla-object->ename gvar_2358 nil)
  )
  (axe-set 'ocbib-isok ls_dcs)
  (setq local_0 ls_abs1e)
  (foreach gvar_2358 local_0
    (vlax-vla-object->ename gvar_2358 polybib-vtxjoin)
  )
  (ls_som0)
)

(defun aoctrl-sihpp (/ local_0 ls_pt2 ls_dc racdyn-calcvtx ls_bulge en_rayon gvar_3160 in_sens in_cote ls_vtxi ls_vtxs1)
  (entdel "ls_abs")
  (ls_som0 're_inv)
  (setq ls_pt2 (re_inv))
  (setq local_0 ls_pt2)
  (foreach ls_dc local_0
    (setq racdyn-calcvtx polybib-vtxjoin)
    (setq ls_bulge nil)
    (setq en_rayon (axedyn-reaccreate ls_dc))
    (setq ls_dc (eo_polyabs ls_dc))
    (setq gvar_3160 (in_param ls_dc 'getpoint))
    (setq in_sens (in_param ls_dc " [Abscisse/Origine/Fin/Milieu 2 points/Décalage d'un point/Repère] :"))
    (setq in_cote (in_param ls_dc "\n -> PolyDyn "))
    (setq ls_vtxi (in_param ls_dc "Origine"))
    (setq ls_vtxs1 (in_param ls_dc 'ls_vtxe))
    (setq racdyn-calcvtx T)
    (if (and gvar_3160 in_sens in_cote ls_vtxi ls_vtxs1 (hachbib-vtxs2hach in_cote) (hachbib-vtxs2hach ls_vtxi) (hachbib-vtxs2hach ls_vtxs1) racdyn-calcvtx)
      (progn
        (if ls_bulge
          (progn
            (ls_som0 (geombib-raccordmax 'croisdyn-tracebordhach2 en_rayon '(ls_pt1 ls_pt2 ls_vtxs ls_vtxe ls_vtxi ls_dc ls_bulge)))
            (ls_som0 'blkbib-get_visiname)
          )
        )
      )
      (progn
        (ls_som0 (geombib-raccordmax '(bo_meme en_bordi en_borde ls_vtxshach en_hachcontour st_layer st_style re_cote) en_rayon 'bo_meme))
        (en_borde (groupbib-list 'en_bordi en_rayon) polybib-vtxjoin)
        (ls_som0 'blkbib-get_visiname)
      )
    )
  )
  (ls_som0 'poly-vtxjoinauto)
)

(defun aoctrl-mpolydyn (/ local_0 local_1 gvar_2300 ha_poly2 importbib-getfilter racdyn-calcvtx ls_bulge en_rayon gvar_3265 aopora-fin ls_importsources poly-vlatrace ls_axe st_sourceid)
  (entdel 'in_add)
  (ls_som0 'in_mod)
  (setq gvar_2300 (in_del))
  (setq ha_poly2 (polybib-lwvertices 'axedyn-reaccreate (ls_dist)))
  (setq local_0 gvar_2300)
  (foreach importbib-getfilter local_0
    (setq racdyn-calcvtx polybib-vtxjoin)
    (setq ls_bulge nil)
    (setq en_rayon (axedyn-reaccreate importbib-getfilter))
    (setq importbib-getfilter (eo_polyabs importbib-getfilter))
    (setq gvar_3265 (in_param importbib-getfilter 'ls_importfilters))
    (setq aopora-fin (in_param importbib-getfilter 'stylepoly-fillcombo))
    (setq ls_importsources (in_param importbib-getfilter "\nBoucle sur les sources"))
    (setq poly-vlatrace (in_param importbib-getfilter 'ls_importsource))
    (setq ls_axe (in_param importbib-getfilter 'dcl-form-show))
    (setq local_1 aopora-fin)
    (and (and aopora-fin ls_importsources poly-vlatrace (axedyn-reaccreate aopora-fin) (axedyn-reaccreate ls_importsources) (axedyn-reaccreate poly-vlatrace) (re_angle (st_ray2 aopora-fin) (st_ray2 ls_importsources) (st_ray2 poly-vlatrace))) (setq racdyn-calcvtx T))
    nil
    (foreach st_sourceid local_1
      (if (odclbib-fillcombo (undobib-start st_sourceid) 'es_ext)
        (progn
          T
          (and racdyn-calcvtx (re_courant (axedyn-reaccreate st_sourceid) (eo_polyabs st_sourceid)))
        )
        (progn
          T
          (and racdyn-calcvtx st_sourceid (re_ray st_sourceid) (fas-polar1 (re_ray st_sourceid)))
        )
      )
      (setq racdyn-calcvtx nil)
    )
    T
    (if racdyn-calcvtx
      (progn
        (if (cadr (laybib-newlay ls_axe ha_poly2))
          (progn
            (st_sourceid en_rayon importbib-getfilter)
            (setq importbib-getfilter (st_rayon importbib-getfilter 'dcl-form-show (axedyn-reaccreate ha_poly2)))
            (setq ls_bulge polybib-vtxjoin)
          )
        )
        (if (and gvar_3265 (re_ray gvar_3265) (fas-polar1 (re_ray gvar_3265)) (cadr T))
          (progn
            (setq ls_bulge polybib-vtxjoin)
          )
        )
        (ls_som0 (geombib-raccordmax "st_filename" en_rayon 'croisdyn-selray))
        (st_linkpath en_rayon)
        T
        (and ls_bulge (ls_som0 'blkbib-get_visiname))
      )
      (progn
        (ls_som0 (geombib-raccordmax "st_filename" en_rayon '(st_nom ls_rays ls_ray st_ray re_ray)))
        (ls_importconfs (groupbib-list '(lambda (ls_importconf) (= st_sourceid (listbib-key (cdr ls_importconf) "st_SourceId"))) en_rayon) polybib-vtxjoin)
        (ls_som0 'blkbib-get_visiname)
      )
    )
  )
  (ls_som0 'poly-vtxjoinauto)
)

(defun aoctrl-polydyn (/ local_0 filebib-odbx ha_poly2 gvar_2284 racdyn-calcvtx ls_bulge en_rayon gvar_3265 ls_axe)
  (entdel 'ls_filters)
  (ls_som0 "\nLecture des entités du ficher source : ")
  (setq filebib-odbx (filebib-odbx))
  (setq ha_poly2 (polybib-lwvertices 'axedyn-reaccreate (ls_dist)))
  (setq local_0 filebib-odbx)
  (foreach gvar_2284 local_0
    (setq racdyn-calcvtx polybib-vtxjoin)
    (setq ls_bulge nil)
    (setq en_rayon (axedyn-reaccreate gvar_2284))
    (setq gvar_2284 (eo_polyabs gvar_2284))
    (setq gvar_3265 (in_param gvar_2284 'ls_importfilters))
    (setq ls_axe (in_param gvar_2284 'dcl-form-show))
    (if racdyn-calcvtx
      (progn
        (if (cadr (laybib-newlay ls_axe ha_poly2))
          (progn
            (ls_layers en_rayon gvar_2284)
            (setq gvar_2284 (st_rayon gvar_2284 'dcl-form-show (axedyn-reaccreate ha_poly2)))
            (setq ls_bulge polybib-vtxjoin)
          )
        )
        (if (and gvar_3265 (re_ray gvar_3265) (fas-polar1 (re_ray gvar_3265)) (cadr T))
          (progn
            (setq ls_bulge polybib-vtxjoin)
          )
        )
        (ls_som0 (geombib-raccordmax 'listbib-remove_doubles en_rayon 'croisdyn-selray))
        (listbib-remove_doubles en_rayon)
        T
        (and ls_bulge (ls_som0 'blkbib-get_visiname))
      )
      (progn
        (ls_som0 (geombib-raccordmax "st_filename" en_rayon '(st_nom ls_rays ls_ray st_ray re_ray)))
        (ls_blks (groupbib-list 'ls_blks en_rayon) polybib-vtxjoin)
        (ls_som0 'blkbib-get_visiname)
      )
    )
  )
  (ls_som0 'poly-vtxjoinauto)
)

(defun croisdyn-set (en_rayon arg_2)
  (fas-rtos3 'ls_polydyn en_rayon arg_2)
)

(defun croisdyn-getparents (aopora-fin / in_cote ls_vtxi gvar_3094)
  (entdel "Projeté")
  (setq in_cote (in_param aopora-fin "\n -> PolyDyn "))
  (setq ls_vtxi (in_param aopora-fin "Origine"))
  (setq gvar_3094 (es_ext in_cote ls_vtxi))
  gvar_3094
)

(defun croisdyn-getelems (ls_resstatus / gvar_2519 gvar_2431 dcl-grid-setcelltext gvar_2257 gvar_2255 gvar_2254 listbib-min gvar_2253)
  (entdel "Emprise")
  (setq gvar_2519 (va_ent ls_resstatus))
  (setq gvar_2431 (in_param gvar_2519 'mpolydyn-set))
  (setq dcl-grid-setcelltext (axedyn-reaccreate (ls_elem "Axe" gvar_2431)))
  (setq gvar_2257 (ls_elem 'ls_restraces gvar_2431))
  (setq gvar_2257 (ls_restraces gvar_2257 "re_rayee"))
  (setq gvar_2255 (axedyn-reaccreate gvar_2257))
  (setq gvar_2254 (ls_vtxsbase2 (in_param gvar_2255 'dcl-form-show)))
  (if (odclbib-fillcombo (in_param gvar_2254 "Impossible de générer les polylignes contours") 1)
    (progn
      (ls_visient (in_param gvar_2254 'intersbib-getinsidevtxs) 'en_polybase)
    )
    (progn
      (in_param gvar_2254 'intersbib-getinsidevtxs)
    )
  )
  (setq listbib-min nil)
  (setq gvar_2255 (dcl-grid-setcurcell gvar_2255 (groupbib-list 'intersbib-getinsidevtxs listbib-min)))
  (setq gvar_2253 (fas-1- gvar_2257))
  (setq gvar_2254 (ls_vtxsbase2 (in_param gvar_2253 'dcl-form-show)))
  (if (odclbib-fillcombo (in_param gvar_2254 "Impossible de générer les polylignes contours") 1)
    (progn
      (ls_visient (in_param gvar_2254 'intersbib-getinsidevtxs) 'en_polybase)
    )
    (progn
      (in_param gvar_2254 'intersbib-getinsidevtxs)
    )
  )
  (setq listbib-min nil)
  (setq gvar_2253 (dcl-grid-setcurcell gvar_2253 (groupbib-list 'intersbib-getinsidevtxs listbib-min)))
  (es_ext dcl-grid-setcelltext gvar_2255 gvar_2253)
)

(defun croisdyn-tracedemiext (projet_md_link_bt_fileedit / local_1 gvar_2225 dcl-form-close gvar_2207 projet_md_link_bt_lineadd gvar_2759_c:projet_md_repblk_oninitialize projet_md_link_bt_linedel ls_fileupdate bo_edit gvar_3388 projet_md_link_bt_import)
  (entdel 'projet_md_link_bt_filedel)
  (setq gvar_2225 (es_ext))
  (setq projet_md_link_bt_fileedit (es_ext))
  (setq dcl-form-close (es_ext))
  (setq local_1 gvar_2224)
  (foreach gvar_2207 local_1
    T
    (and (setq projet_md_link_bt_lineadd (projet_md_link_bt_ok (dcl-grid-addrow 0 gvar_2207) (dcl-grid-addrow 1 gvar_2207) (dcl-grid-addrow 2 gvar_2207) (dcl-grid-addrow 3 gvar_2207) (dcl-grid-addrow 4 gvar_2207) entlast)) (setq projet_md_link_bt_fileedit (dcl-grid-setcurcell projet_md_link_bt_fileedit (axedyn-reaccreate projet_md_link_bt_lineadd))) (setq gvar_2225 (dcl-grid-setcurcell gvar_2225 (va_bande projet_md_link_bt_lineadd))) (setq gvar_2759_c:projet_md_repblk_oninitialize (st_rayon (es_ext (es_ext (groupbib-list 10 (axedyn-reaccreate projet_md_link_bt_lineadd)) (groupbib-list 42 (re_x projet_md_link_bt_lineadd)))) (es_ext (es_ext (groupbib-list 10 (va_bande projet_md_link_bt_lineadd)) (groupbib-list 42 'ha_poly))))) (setq dcl-form-close (dcl-grid-setcurcell dcl-form-close gvar_2759_c:projet_md_repblk_oninitialize)))
  )
  (if (st_blkbase (st_ray2 gvar_2225) 1)
    (progn
      (if (st_blkbase (palbib-init gvar_2245 (axedyn-reaccreate gvar_2225)) (palbib-init gvar_2245 (axedyn-reaccreate projet_md_link_bt_fileedit)))
        (progn
          (setq projet_md_link_bt_linedel 1)
        )
        (progn
          (setq projet_md_link_bt_linedel 255)
        )
      )
      (if (repdyn-getpoint (palbib-init gvar_2245 (axedyn-reaccreate projet_md_link_bt_fileedit)) (palbib-init gvar_2245 (re_x projet_md_link_bt_fileedit)))
        (progn
          (setq ls_fileupdate 1)
        )
        (progn
          (setq ls_fileupdate 255)
        )
      )
      (or (and (and (and (and (re_angle projet_md_link_bt_linedel 1) (re_angle ls_fileupdate 255)) (and (re_angle projet_md_link_bt_linedel 255) (re_angle ls_fileupdate 1))) (and (re_angle projet_md_link_bt_linedel 1) (re_angle ls_fileupdate 1))) (and (re_angle projet_md_link_bt_linedel 255) (re_angle ls_fileupdate 255))) polybib-vtxjoin)
      (setq bo_edit (axedyn-reaccreate dcl-form-close))
      (setq gvar_3388 (palbib-init gvar_2226 (axedyn-reaccreate projet_md_link_bt_fileedit)))
      (setq projet_md_link_bt_import (st_mod gvar_2226 gvar_3388 (re_x projet_md_link_bt_fileedit)))
      (setq projet_md_link_bt_import (bo_active projet_md_link_bt_import (re_x dcl-form-close)))
      (setq gvar_3388 (palbib-init gvar_2245 (axedyn-reaccreate projet_md_link_bt_fileedit)))
      (dcl-tree-clear 1)
      (setq projet_md_link_bt_import (re_x dcl-form-close))
      (setq gvar_3388 (palbib-init gvar_2227 (re_x projet_md_link_bt_fileedit)))
      (setq bo_edit (st_mod gvar_2227 gvar_3388 (axedyn-reaccreate projet_md_link_bt_fileedit)))
      (setq bo_edit (bo_active bo_edit (axedyn-reaccreate dcl-form-close)))
      (setq gvar_3388 (palbib-init gvar_2245 (re_x projet_md_link_bt_fileedit)))
      gvar_2225
    )
    (progn
      nil
    )
  )
)

(defun croisdyn-tracebordhach2 (projet_md_link_bt_fileedit / gvar_2196 gvar_2195 gvar_2194 gvar_2192 in_num blkbib-getparententities ls_elems1 ls_axe gvar_2827 gvar_2408 listbib-min ls_in)
  (entdel 'ls_importconf)
  (setq gvar_2196 (repdyn-getpoint (palbib-init gvar_2245 (in_param (fas-1- bo_edit) 10)) (palbib-init gvar_2245 (in_param (axedyn-reaccreate bo_edit) 10))))
  (setq gvar_2195 (*en_ray* bo_edit nil))
  (setq gvar_2194 (*en_ray* projet_md_link_bt_import nil))
  (setq gvar_2192 (axedyn-reaccreate (dcl-tree-addchild (es_ext gvar_2200 projet_md_link_bt_import bo_edit) '(st_blk1 st_blk2 ls_blk st_msg bo_go))))
  (setq projet_md_link_bt_fileedit (*en_ray* gvar_2192 (es_ext (groupbib-list 70 1))))
  (setq in_num (dcl-grid-setcurcell in_num projet_md_link_bt_fileedit))
  (setq blkbib-getparententities (in_param (dcl-grid-addrow 0 gvar_2233) "Repère"))
  (setq ls_elems1 (rem (en_ext2 (es_ext projet_md_link_bt_fileedit) nil 'en_ext1 'ha_poly 1 nil (es_ext (groupbib-list "Choix d'un fichier source" gvar_2190) (groupbib-list "Appliquer" blkbib-getparententities)))))
  (setq in_num (dcl-grid-setcurcell in_num ls_elems1))
  (setq ls_axe (in_param (dcl-grid-addrow 1 gvar_2233) 'dcl-form-show))
  (setq gvar_2827 (ls_visient 255 gvar_2232 (in_param (dcl-grid-addrow 1 gvar_2233) 'ls_croiselems)))
  (setq gvar_2408 (ls_visient 255 gvar_2232 (in_param (dcl-grid-addrow 1 gvar_2233) "re_rayee")))
  (if (repdyn-getpoint gvar_2827 'ha_poly)
    (progn
      (column gvar_2195)
      (setq listbib-min (in_param (dcl-grid-addrow 1 gvar_2233) 'intersbib-getinsidevtxs))
      (setq listbib-min (ls_visient projet_md_link_bt_fileedit listbib-min))
      (setq ls_in (axedyn-reaccreate (st_path gvar_2195 listbib-min)))
      (setq gvar_2195 (rem ls_in))
    )
  )
  gvar_2195
  'ha_poly
  (repdyn-get gvar_2195)
  255
  gvar_2827
  (if gvar_2196
    (progn
      255
    )
    (progn
      1
    )
  )
  (en_refoffset (ls_visient) 'ls_ext1 'ls_ext1 1 nil ls_axe)
  (setq ls_axe (in_param (dcl-grid-addrow 2 gvar_2233) 'dcl-form-show))
  (setq gvar_2827 (ls_visient gvar_2232 (in_param (dcl-grid-addrow 2 gvar_2233) 'ls_croiselems)))
  (setq gvar_2408 (ls_visient gvar_2232 (in_param (dcl-grid-addrow 2 gvar_2233) "re_rayee")))
  (if (repdyn-getpoint gvar_2827 'ha_poly)
    (progn
      (column gvar_2194)
      (setq listbib-min (in_param (dcl-grid-addrow 1 gvar_2233) 'intersbib-getinsidevtxs))
      (setq listbib-min (ls_visient 255 projet_md_link_bt_fileedit listbib-min))
      (setq ls_in (axedyn-reaccreate (st_path gvar_2194 listbib-min)))
      (setq gvar_2194 (rem ls_in))
    )
  )
  gvar_2194
  'ha_poly
  (repdyn-get gvar_2194)
  gvar_2827
  (if gvar_2196
    (progn
      255
    )
    (progn
      1
    )
  )
  (en_refoffset (ls_visient) 'ls_ext1 'ls_ext1 1 nil ls_axe)
  (en_ref1 (es_ext gvar_2195 gvar_2194 projet_md_link_bt_fileedit))
)

(defun c:projet_pa_croisdyn_oninitialize (/ local_0 gvar_3345 in_lon0 gvar_2276 gvar_2275 stealbib-go gvar_2273 vlax-ldata-delete axedyn-set)
  (entdel 'atoi)
  (bo_lctabs gvar_2186 in_lon0)
  (setq gvar_3345 (ls_polydyn re_yinv))
  (setq in_lon0 (in_param gvar_3345 'ls_obj))
  (setq gvar_2276 (in_param gvar_3345 "\nEntités modifiées  : "))
  (setq gvar_2275 (in_param gvar_3345 "\nEntités supprimées : "))
  (setq stealbib-go (in_param gvar_3345 "AO-ImportSources"))
  (setq gvar_2273 (in_param gvar_3345 "AO-ImportConfs"))
  (setq vlax-ldata-delete (es_ext (groupbib-list linkbib-confdel gvar_2276) (groupbib-list st_confid gvar_2275) (groupbib-list bo_ents stealbib-go) (groupbib-list gvar_2182 gvar_2273)))
  (setq local_0 vlax-ldata-delete)
  nil
  (foreach axedyn-set local_0
    (bo_lctabs (axedyn-reaccreate axedyn-set) (eo_blkbase (eo_polyabs axedyn-set) 2 3))
  )
)

(defun croisdyn-selray (ls_parent ls_importsource0 subst label / st_syle st_nom st_axedynid ld_axedyn local_4 gvar_2265 in_cote ls_vtxi gvar_2244 gvar_2243 blkpoly-get stringbib-str2lst gr_filterupdate projet_md_link_bt_lineadd)
  (entdel 'key)
  (sihpp-list label)
  (setq gvar_2265 gvar_3345)
  (setq in_cote (in_param gvar_2265 "\n -> PolyDyn "))
  (setq ls_vtxi (in_param gvar_2265 "Origine"))
  (setq gvar_2244 (ls_deb (eo_polyabs in_cote)))
  (setq gvar_2243 (ls_deb (eo_polyabs ls_vtxi)))
  (setq blkpoly-get (in_param (fas-polar1 (re_ray (in_param gvar_2265 " [Abscisse/Origine/Fin/Milieu 2 points/Décalage d'un point/Repère] :"))) 10))
  (setq stringbib-str2lst (in_param gvar_2244 ls_parent))
  (setq gr_filterupdate (in_param gvar_2243 ls_importsource0))
  (setq projet_md_link_bt_lineadd (projet_md_link_bt_ok (re_ray stringbib-str2lst) (re_ray gr_filterupdate) subst label gvar_3331 blkpoly-get))
  (if projet_md_link_bt_lineadd
    (progn
      (ls_options (dcl-forcedwgredraw label) 80)
      (ls_options (dcl-forcedwgredraw label) 're_long)
      (ls_options (dcl-forcedwgredraw label) 4)
      (setq st_axedynid (st_rayon (es_ext (es_ext (groupbib-list 10 (va_bande projet_md_link_bt_lineadd)) (groupbib-list 40 'ha_poly) (groupbib-list 41 'ha_poly) (groupbib-list 42 (dcl-grid-addrow (re_x projet_md_link_bt_lineadd))))) (es_ext (es_ext (groupbib-list 10 (axedyn-reaccreate projet_md_link_bt_lineadd)) (groupbib-list 40 'ha_poly) (groupbib-list 41 'ha_poly) (groupbib-list 42 'ha_poly)))))
      (setq label (gr_filterupdate st_axedynid nil))
      (boxlib-optionbox label 4)
    )
    (progn
      nil
    )
  )
)

(defun c:projet_pa_croisdyn_re_rayee_onsetfocus ()
  (ls_entnew linkbib-confdel 0 255)
  (boxlib-optionbox 'ls_childs 'ls_childs 1 1 (in_param gvar_3345 "\nEntités modifiées  : "))
)

(defun c:projet_pa_croisdyn_re_rayei_onsetfocus ()
  (ls_entnew st_confid 0 255)
  (boxlib-optionbox 'ls_childs 'parentbib-getson 1 255 (in_param gvar_3345 "\nEntités supprimées : "))
)

(defun c:projet_pa_croisdyn_re_rayie_onsetfocus ()
  (ls_entnew bo_ents 0 255)
  (boxlib-optionbox 'parentbib-getson 'ls_childs 255 1 (in_param gvar_3345 "AO-ImportSources"))
)

(defun c:projet_pa_croisdyn_re_rayii_onsetfocus ()
  (ls_entnew gvar_2182 0 255)
  (boxlib-optionbox 'parentbib-getson 'parentbib-getson 255 255 (in_param gvar_3345 "AO-ImportConfs"))
)

(defun importbib-getfilter ()
  nil
)

(defun c:projet_md_link_oninitialize (/ local_0 ls_common)
  (re_haut re_haut)
  (setq ls_common (es_ext (es_ext "Sauver filtre" '(ls_importconf st_option ls_linktype) '(lambda (ls_columntype va_style) (cons ls_columntype va_style)) 6 "Choisir le type de réseau") (es_ext 'ls_rowcol '(ls_importconf st_option ls_linktype) '(lambda (ls_columntype va_style) (cons ls_columntype va_style)) 0 'st_btn) (es_ext 'dcl-grid-deleterow '(ls_importsource ld_ldata) '(lambda (ls_columntype va_style) (cons ls_columntype va_style)) 6 "Choisir le type de réseau") (es_ext 'doc '(ls_importsource ld_ldata) '(ls_objs obj eg_obj st_type ls_common) 0 'ls_ext1) (es_ext 'ls_objs 'cvport 'paperspace 6 "Choisir le type de réseau") (es_ext 'modelspace 'collect-init 'obj 0 4) (es_ext 'collect-next 'eg_obj '(lambda (ls_columntype va_style) (cons ls_columntype va_style)) 6 "Choisir le type de réseau") (es_ext 'dcl-form-show "ha_handle" 'obj 0 1) (es_ext 'vla-get-linetype 'vla-get-linetypescale 'vla-get-truecolor 9 '(va_point re_abs pt_base pt_1 pt_2 re_abs1 re_abs2)) (es_ext 'intersbib-getinsidevtxs 'vla-get-linetypescale 'vla-get-truecolor 9 'ha_poly)))
  (setq local_0 (eo_plf gvar_2078))
  (while (<= local_0 0)
    (eo_plf gvar_2078 0)
    (setq local_0 (1- local_0))
  )
  (vlax-vla-object->ename covplf-getvtxs nil)
  (vlax-vla-object->ename covplf-getprops nil)
  (vlax-vla-object->ename ls_protype nil)
  (vlax-vla-object->ename gvar_2072 polybib-vtxjoin)
  (vlax-vla-object->ename vla-get-closed nil)
  (vlax-vla-object->ename vla-get-linetypegeneration nil)
  (vlax-vla-object->ename gvar_2069 polybib-vtxjoin)
  (vlax-invoke covplf-getvtxs 'vla-get-effectivename)
  (vlax-vla-object->ename vla-get-layer polybib-vtxjoin)
  (vlax-vla-object->ename gvar_2078 nil)
  (vlax-vla-object->ename vla-get-rotation nil)
  (vlax-vla-object->ename gvar_2065 nil)
  (covfou-getchambspecs)
)

(defun ls_fileupdate (/ local_0 ls_columntypes vla-get-patternname)
  (entdel 'covassbib-getpipe)
  (covassbib-getpipevtxs gvar_2069)
  (setq local_0 ls_columns)
  (foreach ls_columntypes local_0
    (covassbib-getpipevtxs gvar_2069 (in_param (eo_polyabs ls_columntypes) 'st_columntype) (dcl-grid-addrow 0 ls_columntypes))
  )
  (setq local_0 dcl-grid-setitemdroplist)
  nil
  (foreach vla-get-patternname local_0
    (vla-get-backgroundcolor gvar_2069 (es_ext (es_ext (in_param (eo_polyabs vla-get-patternname) 'vla-get-patternscale) (in_param (eo_polyabs vla-get-patternname) 'vla-get-patternangle) (geombib-raccordmax (in_param (eo_polyabs vla-get-patternname) 'vla-get-patternscale) 'vla-get-backgroundcolor (dcl-grid-addrow 0 vla-get-patternname)))))
  )
)

(defun c:projet_md_link_bt_fileadd_onclicked (/ blkbib-blkeffname gvar_2049 vl-remove ls_columns)
  (entdel 'listbib-addonce)
  (setq blkbib-blkeffname (projet_pa_bordyn_st_style 'path (trans "OC-Bordyn") 'vlax-property-available-p 16))
  (if ls_columns
    (progn
      (setq gvar_2049 (polybib-lwvertices 'axedyn-reaccreate ls_columns))
      (setq gvar_2049 (polybib-lwvertices 'ha_handle gvar_2049))
      (setq vl-remove (projet_pa_croisdyn gvar_2049))
    )
    (progn
      (setq vl-remove 0)
    )
  )
  (setq ls_columns (dcl-grid-setcurcell ls_columns (es_ext (dcl-control-setenabled (st_axeid vl-remove)) (groupbib-list 'st_columntype (vlax-curve-getclosestpointto blkbib-blkeffname)) (groupbib-list '(column row st_columntype st_label) (re_param blkbib-blkeffname)))))
  (covfou-getchambspecs)
)

(defun c:projet_md_link_bt_filedel_onclicked (/ local_0 ls_columntypes ls_columns vla-get-patternname)
  (entdel 'importbib-tracecovagrad)
  (setq local_0 dcl-grid-setitemdroplist)
  (and gr_filteraddline (setq ls_columntypes (re_angle0 gr_filteraddline ls_columns)) (setq ls_columns (blkpolydial-getpoint ls_columntypes ls_columns)))
  nil
  (foreach vla-get-patternname local_0
    (if (re_angle (re_angle0 'vla-get-patternscale vla-get-patternname) gr_filteraddline)
      (progn
        (importbib-tracehach (dcl-grid-addrow 0 vla-get-patternname) nil)
      )
      (progn
        nil
      )
    )
  )
  T
  T
)

(defun linkbib-confdel (importbib-tracecovamanhole importbib-tracepoly / local_2 vla-get-patternname dcl-grid-setitemdroplist gvar_3094 st_bloc)
  (entdel '(ls_parentconf en_ent))
  (ls_parentconf 'dcl-messagebox importbib-tracecovamanhole)
  (setq vla-get-patternname (re_angle0 importbib-tracecovamanhole dcl-grid-setitemdroplist))
  (setq dcl-grid-setitemdroplist (blkpolydial-getpoint vla-get-patternname dcl-grid-setitemdroplist))
  (setq gvar_3094 (re_courant 'dcl-messagebox importbib-tracecovamanhole))
  (if importbib-tracepoly
    (progn
      (setq local_2 gvar_3094)
      nil
      (foreach st_bloc local_2
        (sihpp-list (re_ray (eo_polyabs st_bloc)))
      )
    )
    (progn
      nil
    )
  )
)

(defun c:projet_md_link_bt_fileedit_onclicked (/ blkbib-blkeffname blkbib-blk_mod ls_columntypes ls_columns)
  T
  (and gr_filteraddline (setq blkbib-blkeffname (projet_pa_bordyn_st_style 'path (trans "OC-Bordyn") 'vlax-property-available-p 16)) (setq blkbib-blk_mod (re_angle0 gr_filteraddline ls_columns)) (setq ls_columntypes (es_ext (dcl-grid-addrow 0 blkbib-blk_mod) (groupbib-list 'st_columntype (vlax-curve-getclosestpointto blkbib-blkeffname)) (groupbib-list '(column row st_columntype st_label) (re_param blkbib-blkeffname)))) (setq ls_columns (ha_handle2 ls_columntypes blkbib-blk_mod ls_columns)))
)

(defun c:projet_md_link_tv_file_onselchanged (/ importbib-isvalid ls_conf ls_filter ls_props en_ent local_0 importbib-tracecovamanhole gr_filteraddline)
  (if (importbib-isvalid 'vla-get-backgroundcolor importbib-isvalid_2)
    (progn
      (ha_import importbib-tracecovamanhole)
      (setq importbib-tracecovamanhole (re_x (ha_import importbib-isvalid_2 'vla-get-backgroundcolor)))
      (setq gr_filteraddline (axedyn-reaccreate (ha_import importbib-isvalid_2 'vla-get-backgroundcolor)))
    )
    (progn
      (setq gr_filteraddline importbib-isvalid_2)
      (setq importbib-tracecovamanhole nil)
    )
  )
  (vlax-vla-object->ename ls_protype polybib-vtxjoin)
  (vlax-vla-object->ename covplf-getprops T)
  (vlax-vla-object->ename covplf-getvtxs T)
  (vlax-vla-object->ename st_network nil)
  (vlax-vla-object->ename vla-get-closed (cadr importbib-tracecovamanhole))
  (vlax-vla-object->ename vla-get-linetypegeneration (cadr importbib-tracecovamanhole))
  (vlax-vla-object->ename gvar_2072 polybib-vtxjoin)
  (and importbib-tracecovamanhole importbib-tracecovamanhole)
)

(defun c:projet_md_link_bt_entadd_onclicked (/ gvar_2031 intersbib-getent gvar_2049 vl-remove dcl-grid-setitemdroplist)
  (entdel 'en_import)
  (setq gvar_2031 (polybib-lwvertices 'eg_import in_status))
  (setq intersbib-getent (bo_inv0 'ls_intersent 'ls_abss gvar_2031 nil))
  (if dcl-grid-setitemdroplist
    (progn
      (setq gvar_2049 (polybib-lwvertices 'axedyn-reaccreate dcl-grid-setitemdroplist))
      (setq gvar_2049 (polybib-lwvertices 'ha_handle gvar_2049))
      (setq vl-remove (projet_pa_croisdyn gvar_2049))
    )
    (progn
      (setq vl-remove 0)
    )
  )
  (setq dcl-grid-setitemdroplist (dcl-grid-setcurcell dcl-grid-setitemdroplist (es_ext (dcl-control-setenabled (st_axeid vl-remove)) (groupbib-list 'vla-get-patternscale gr_filteraddline) (groupbib-list 'vla-get-patternangle intersbib-getent) (groupbib-list 'ha_inters nil))))
  (covfou-getchambspecs)
)

(defun c:projet_md_link_bt_entdel_onclicked ()
  (entdel 'ls_abscrois)
  T
  (and (re_angle 6 (ls_ptinint '(lambda (x) (polybib-absproj en_poly (vlax-curve-getpointatdist en_ref2 x))) '(lambda (x) (cons x (list x x "CR"))) 15)) (importbib-tracehach importbib-tracecovamanhole polybib-vtxjoin))
)

(defun gr_filterupdate (importbib-tracecovamanhole / local_1 vla-get-patternname intersbib-getent ha_poly2 ls_absint ls_absext ls_ptint eq gvar_2519)
  (entdel 'ls_ptintext)
  (ls_ptintext intersbib-getent)
  (*en_ins* gvar_2078)
  (setq vla-get-patternname (in_param dcl-grid-setitemdroplist importbib-tracecovamanhole))
  (setq intersbib-getent (in_param vla-get-patternname 'vla-get-patternangle))
  (setq ha_poly2 (in_param vla-get-patternname 'ha_inters))
  (setq ls_absint (re_angle0 intersbib-getent in_status))
  (setq ls_absext (dcl-grid-addrow 2 ls_absint))
  (setq ls_ptint (polybib-lwvertices 'axedyn-reaccreate ls_absext))
  (setq eq 0)
  (setq local_1 ha_poly2)
  nil
  (foreach gvar_2519 local_1
    (ls_ptint gvar_2519 ls_ptint)
    (setq eq (st_axeid eq))
  )
)

(defun gr_filteraddline (arg_1 ls_ptint / local_2 netbib-purgeblock eq ls_abss2 listbib-groupbynum)
  (entdel 'listbib-sort)
  (setq netbib-purgeblock 0)
  (setq eq (eo_blkpop gvar_2078 'ls_ext1))
  (setq local_2 ls_ptint)
  nil
  (foreach ls_abss2 local_2
    (setq listbib-groupbynum (in_param arg_1 ls_abss2))
    (or (or (or (re_angle 'modelspace ls_abss2) (re_angle 'dcl-form-show ls_abss2)) (re_angle 'intersbib-getinsidevtxs ls_abss2)) (re_angle 'vla-get-linetype ls_abss2))
    (setq listbib-groupbynum (eo_blkbase listbib-groupbynum 2 3))
    (setq listbib-groupbynum (eo_blkbase listbib-groupbynum 2 3))
    (ls_ab gvar_2078 eq (st_axeid netbib-purgeblock) 18)
    (ls_chem gvar_2078 eq (st_axeid netbib-purgeblock) (polybib-lwvertices 'eo_polyabs ls_importconfnew))
    (setq listbib-groupbynum (en_polyabs ls_importconfnew listbib-groupbynum 'ls_filter))
    (ls_ab gvar_2078 eq (st_axeid netbib-purgeblock) 18)
    (ls_chem gvar_2078 eq (st_axeid netbib-purgeblock) (polybib-lwvertices 'eo_polyabs dcl-grid-getrowcount))
    (en_blk gvar_2078 eq (st_axeid netbib-purgeblock) listbib-groupbynum)
    (setq listbib-groupbynum (en_polyabs dcl-grid-getrowcount listbib-groupbynum '(inc ls_filters ls_filter)))
    (setq netbib-purgeblock (st_axeid netbib-purgeblock))
  )
)

(defun c:projet_md_link_gr_filter_ondblclicked (/ eq netbib-purgeblock vla-get-patternname intersbib-getent ls_absint re_angle2 pt_21 ls_axe gvar_1996 dcl-listbox-clear blkbib-getparententities)
  (setq vla-get-patternname (in_param dcl-grid-setitemdroplist importbib-tracecovamanhole))
  (setq intersbib-getent (in_param vla-get-patternname 'vla-get-patternangle))
  (setq ls_absint (re_angle0 intersbib-getent in_status))
  (setq re_angle2 (polybib-lwvertices 'axedyn-reaccreate (dcl-grid-addrow 2 ls_absint)))
  (setq pt_21 (dcl-grid-addrow (vla-get-name netbib-purgeblock_2) re_angle2))
  nil
  (or (or (or (re_angle pt_21 'ls_rowcol) (re_angle pt_21 'doc)) (re_angle pt_21 'modelspace)) (re_angle pt_21 'dcl-form-show))
  (if (setq ls_axe (bo_inv0 'pt_22 'en_poly2 (polybib-lwvertices 'ls_ptint2 ls_importconfnew) nil))
    (progn
      (en_blk gvar_2078 eq_2 netbib-purgeblock_2 (in_param ls_importconfnew (ha_handle ls_axe)))
    )
    (progn
      nil
    )
  )
  (if (setq gvar_1996 (bo_inv0 'pt_22 '(lambda (x) (cons (car x) (list (car x) en_poly2 (car x) en_poly2))) (polybib-lwvertices 'ls_absint2 dcl-grid-getrowcount) nil))
    (progn
      (en_blk gvar_2078 eq_2 netbib-purgeblock_2 (in_param dcl-grid-getrowcount (ha_handle gvar_1996)))
    )
    (progn
      nil
    )
  )
  (if (setq dcl-listbox-clear (ls_absint2 'ls_ext1 nil nil))
    (progn
      (en_blk gvar_2078 eq_2 netbib-purgeblock_2 dcl-listbox-clear)
    )
    (progn
      nil
    )
  )
  (if (setq blkbib-getparententities (vlax-curve-getstartpoint (ls_absint2 gvar_2078 eq_2 netbib-purgeblock_2)))
    (progn
      (en_blk gvar_2078 eq_2 netbib-purgeblock_2 blkbib-getparententities)
    )
    (progn
      nil
    )
  )
)

(defun c:projet_md_link_bt_import_onclicked (/ local_0 ha_poly2 ls_columntypes vla-get-patternname stylebord-list intersbib-getent ls_absint ls_absext ls_ptint gvar_2519)
  (entdel '(lambda (x) (list (cdr x) (polybib-absatpoint en_ent (vlax-curve-getpointatdist en_poly (cdr x))))))
  (setq ha_poly2 nil)
  (setq ls_columntypes (in_param ls_columns gr_filteraddline))
  (setq vla-get-patternname (eo_polyabs (in_param dcl-grid-setitemdroplist importbib-tracecovamanhole)))
  (setq stylebord-list (geombib-raccordmax (in_param ls_columntypes '(column row st_columntype st_label)) '(en_poly ha_poly ld_poly ha_axe ha_ext ls_ray ls_ent in_node re_courant st_txt) (in_param ls_columntypes 'st_columntype) 'st_flag))
  (setq intersbib-getent (in_param vla-get-patternname 'vla-get-patternangle))
  (or (or (or (or (or (re_angle intersbib-getent "Fin BlKPoly-XY2WCS") (re_angle intersbib-getent 'importbib-getcovapipe)) (re_angle intersbib-getent 'foubib-getvtxs)) (re_angle intersbib-getent 'collect-release)) (re_angle intersbib-getent 'ls_specs)) (re_angle intersbib-getent 'projet_pa_detail_btn_param))
  (setq ha_poly2 (es_poly (dcl-grid-addcolumns 'vlax-curve-getstartpoint (es_ext stylebord-list) nil)))
  (setq ha_poly2 (es_poly (dcl-grid-addcolumns 'poly-polyinside (es_ext stylebord-list) nil)))
  (setq ha_poly2 (es_poly (dcl-grid-addcolumns '(lambda (x) (eq (caar ls_abs) (car x))) (es_ext stylebord-list) nil)))
  (setq ha_poly2 (es_poly (dcl-grid-addcolumns 'vl-remove-if (es_ext stylebord-list) nil)))
  (setq ha_poly2 (es_poly (dcl-grid-addcolumns 'vlax-curve-getendpoint (es_ext stylebord-list) nil)))
  (setq ha_poly2 (es_poly (dcl-grid-addcolumns '(lambda (x) (eq (car (last ls_abs)) (car x))) (es_ext stylebord-list) nil)))
  (if ha_poly2
    (progn
      (ha_import importbib-tracecovamanhole)
      (setq ls_absint (re_angle0 intersbib-getent in_status))
      (setq ls_absext (dcl-grid-addrow 2 ls_absint))
      (setq ls_ptint (polybib-lwvertices 'axedyn-reaccreate ls_absext))
      (setq local_0 ha_poly2)
      (foreach gvar_2519 local_0
        (ls_ptint gvar_2519 ls_ptint)
      )
    )
  )
  (ls_som0)
)

(defun c:projet_md_link_gr_filter_onselchanged (/ eq netbib-purgeblock)
  (entdel '(ha_ref ls_ref))
  (ls_som0)
)

(defun c:projet_md_link_bt_save_onclicked (/ local_0 local_1 eq vla-get-patternname intersbib-getent ls_absint re_angle2 gvar_2149 ls_ref netbib-purgeblock ha_ref mpolydyn-get dcl-grid-setitemdroplist gvar_2127)
  (entdel 'ename)
  (if gvar_2127
    (progn
      (setq eq 0)
      (setq vla-get-patternname (in_param dcl-grid-setitemdroplist importbib-tracecovamanhole))
      (setq intersbib-getent (in_param vla-get-patternname 'vla-get-patternangle))
      (setq ls_absint (re_angle0 intersbib-getent in_status))
      (setq re_angle2 (polybib-lwvertices 'axedyn-reaccreate (dcl-grid-addrow 2 ls_absint)))
      (setq gvar_2149 (es_ext))
      (setq local_0 (ename gvar_2078))
      (while (<= local_0 0)
        (setq local_0 (1- local_0))
        (setq ls_ref (es_ext))
        (setq netbib-purgeblock 0)
        (setq local_1 (vla-get-name (eo_plf gvar_2078)))
        (while (<= local_1 0)
          (setq local_1 (1- local_1))
          (setq ha_ref (ls_absint2 gvar_2078 eq (st_axeid netbib-purgeblock)))
          (or (or (or (re_angle (dcl-grid-addrow netbib-purgeblock re_angle2) 'modelspace) (re_angle (dcl-grid-addrow netbib-purgeblock re_angle2) 'intersbib-getinsidevtxs)) (re_angle (dcl-grid-addrow netbib-purgeblock re_angle2) 'vla-get-linetype)) (re_angle (dcl-grid-addrow netbib-purgeblock re_angle2) 'dcl-form-show))
          (setq ha_ref (axedyn-reaccreate (dcl-grid-addrow (laybib-newlay ha_ref (polybib-lwvertices 'eo_polyabs ls_importconfnew)) ls_importconfnew)))
          (setq ha_ref (groupbib-listobj ha_ref))
          (setq ha_ref (groupbib-listobj ha_ref))
          (setq ha_ref (axedyn-reaccreate (dcl-grid-addrow (laybib-newlay ha_ref (polybib-lwvertices 'eo_polyabs dcl-grid-getrowcount)) dcl-grid-getrowcount)))
          (setq ls_ref (dcl-grid-setcurcell ls_ref (groupbib-list (dcl-grid-addrow netbib-purgeblock re_angle2) ha_ref)))
          (setq netbib-purgeblock (st_axeid netbib-purgeblock))
        )
        (setq gvar_2149 (dcl-grid-setcurcell gvar_2149 ls_ref))
        (setq eq (st_axeid eq))
      )
      (vlax-vla-object->ename gvar_2069 polybib-vtxjoin)
      (vlax-invoke covplf-getvtxs 'vla-get-effectivename)
      (vlax-vla-object->ename covplf-getprops nil)
      (vlax-vla-object->ename ls_protype nil)
      (vlax-vla-object->ename gvar_2072 nil)
      (vlax-vla-object->ename vla-get-closed nil)
      (vlax-vla-object->ename vla-get-linetypegeneration nil)
      (vlax-vla-object->ename st_network nil)
      (vlax-vla-object->ename vla-get-layer polybib-vtxjoin)
      (vlax-vla-object->ename gvar_2078 nil)
      (vlax-vla-object->ename vla-get-rotation nil)
      (vlax-vla-object->ename gvar_2065 nil)
      (setq mpolydyn-get (groupbib-list importbib-tracecovamanhole (st_rayon vla-get-patternname 'ha_inters gvar_2149)))
      (setq dcl-grid-setitemdroplist (ha_handle2 mpolydyn-get (re_angle0 importbib-tracecovamanhole dcl-grid-setitemdroplist) dcl-grid-setitemdroplist))
      (setq gvar_2127 nil)
    )
    (progn
      (vlax-vla-object->ename gvar_2069 nil)
      (vlax-invoke covplf-getvtxs 'racdyn-get)
      (vlax-vla-object->ename covplf-getprops nil)
      (vlax-vla-object->ename ls_protype nil)
      (vlax-vla-object->ename gvar_2072 nil)
      (vlax-vla-object->ename vla-get-closed nil)
      (vlax-vla-object->ename vla-get-linetypegeneration nil)
      (vlax-vla-object->ename st_network polybib-vtxjoin)
      (vlax-vla-object->ename vla-get-layer nil)
      (vlax-vla-object->ename gvar_2078 polybib-vtxjoin)
      (vlax-vla-object->ename vla-get-rotation polybib-vtxjoin)
      (vlax-vla-object->ename gvar_2065 polybib-vtxjoin)
      (setq gvar_2127 polybib-vtxjoin)
    )
  )
)

(defun c:projet_md_link_bt_lineadd_onclicked (/ vla-get-patternname intersbib-getent ls_absint ls_absext ls_ptint gvar_2519)
  (entdel "ha_rac")
  (ls_ptint gvar_2519 ls_ptint)
  (setq vla-get-patternname (in_param dcl-grid-setitemdroplist importbib-tracecovamanhole))
  (setq intersbib-getent (in_param vla-get-patternname 'vla-get-patternangle))
  (setq ls_absint (re_angle0 intersbib-getent in_status))
  (setq ls_absext (dcl-grid-addrow 2 ls_absint))
  (setq ls_ptint (polybib-lwvertices 'axedyn-reaccreate ls_absext))
  (setq gvar_2519 (polybib-lwvertices '(ls_axes ls_axe st_axeid ha_group ls_obj) ls_absext))
  (setq gvar_2519 (polybib-lwvertices 'polydyn-get ls_ptint gvar_2519))
  (ls_som0)
)

(defun c:projet_md_link_bt_linedel_onclicked (/ gvar_1976)
  (if (and (setq gvar_1976 (blkpoly-ls_entsnew gvar_2078)) (st_blkbase (axedyn-reaccreate gvar_1976) 255))
    (progn
      (polydyn-get gvar_2078 (axedyn-reaccreate gvar_1976))
    )
    (progn
      nil
    )
  )
)

(defun c:projet_md_link_bt_ok_onclicked (/ local_0 gvar_3164 ls_columntypes vla-get-patternname)
  (entdel "\nEntité non prise en charge")
  (re_abs1 re_haut 1)
  (setq local_0 (axedyn-setrayext '(lambda (doc) (importbib-getpipesstyles doc))))
  (foreach gvar_3164 local_0
    (ls_parentconf '(lambda (doc) (importbib-getpipesstyles doc)) (axedyn-reaccreate gvar_3164))
  )
  (setq local_0 ls_columns)
  (foreach ls_columntypes local_0
    (fas-rtos3 '(lambda (doc) (importbib-getpipesstyles doc)) (axedyn-reaccreate ls_columntypes) (eo_polyabs ls_columntypes))
  )
  (setq local_0 (axedyn-setrayext '(lambda (doc) (importbib-getmanholestyles doc))))
  (foreach gvar_3164 local_0
    (ls_parentconf '(lambda (doc) (importbib-getmanholestyles doc)) (axedyn-reaccreate gvar_3164))
  )
  (setq local_0 dcl-grid-setitemdroplist)
  (foreach vla-get-patternname local_0
    (fas-rtos3 '(lambda (doc) (importbib-getmanholestyles doc)) (axedyn-reaccreate vla-get-patternname) (eo_polyabs vla-get-patternname))
  )
  (ls_som0)
)

(defun c:projet_md_link_bt_cancel_onclicked ()
  (re_abs1 re_haut 2)
)

(defun importbib-getcovaduct (arg_1 / en_leg eo_leg pt_dyn pt_ins re_angle re_side1 re_side2 re_dist ls_linktype ls_columns local_0 local_2 dcl-form-close projet_md_metzon_tb_coef gvar_1943_c:projet_md_metzon_tb_coef_onsetfocus in_lon0 projet_md_metzon listbib-min gvar_1941_c:projet_md_metzon_bt_pick_onclicked gvar_2607 ls_ref gvar_2149 polybib_geom-bulge2radius st_blk)
  (entdel '(el_ent projet_md_metzon_oninitialize projet_md_metzon_bt_ok_onclicked projet_md_metzon_bt_annuler_onclicked))
  (setq dcl-form-close (projet_md_metzon_tb_larg gvar_1966))
  (setq projet_md_metzon_tb_coef (c:projet_md_metzon_tb_larg_onsetfocus gvar_1966))
  (setq gvar_1943_c:projet_md_metzon_tb_coef_onsetfocus (dcl-grid-addrow 0 projet_md_metzon_tb_coef))
  (setq in_lon0 (dcl-grid-addrow 1 projet_md_metzon_tb_coef))
  (setq projet_md_metzon (dcl-grid-addrow 2 projet_md_metzon_tb_coef))
  (setq listbib-min (dcl-grid-addrow 3 projet_md_metzon_tb_coef))
  (setq gvar_1941_c:projet_md_metzon_bt_pick_onclicked (dcl-grid-addrow 4 projet_md_metzon_tb_coef))
  (setq gvar_2607 nil)
  (while (and (cadr gvar_2607) gvar_2149)
    T
    (setq ls_ref (axedyn-reaccreate gvar_2149))
    (setq gvar_2149 (eo_polyabs gvar_2149))
    (and (or (or (re_angle (in_param ls_ref 'modelspace) 4) (re_angle (in_param ls_ref 'modelspace) projet_md_metzon)) (or (re_angle (in_param ls_ref 'collect-next) "Choisir le type de réseau") (re_angle (in_param ls_ref 'collect-next) gvar_1943_c:projet_md_metzon_tb_coef_onsetfocus))) (setq gvar_2607 polybib-vtxjoin))
  )
  (if gvar_2607
    (progn
      (setq polybib_geom-bulge2radius (in_param arg_1 'polybib-absatpoint))
      (setq polybib_geom-bulge2radius (st_rayon polybib_geom-bulge2radius 8 (in_param ls_ref 'ls_rowcol)))
      (setq arg_1 (st_rayon arg_1 'polybib-absatpoint polybib_geom-bulge2radius))
      (setq polybib_geom-bulge2radius (st_rayon polybib_geom-bulge2radius (es_ext (groupbib-list 'dcl-project-load listbib-min))))
      (setq arg_1 (st_rayon arg_1 'polybib-absatpoint polybib_geom-bulge2radius))
      (setq st_blk (st_rayon arg_1 (es_ext (groupbib-list 'collect-next gvar_1943_c:projet_md_metzon_tb_coef_onsetfocus) (groupbib-list 'ls_obj in_lon0) (groupbib-list 'projet_md_metzon_cb_prop projet_md_metzon) (groupbib-list 'intersbib-getinsidevtxs listbib-min) (groupbib-list 'dcl-combobox-clear gvar_1941_c:projet_md_metzon_bt_pick_onclicked) (groupbib-list 'blkpolydial-getrep dcl-form-close))))
    )
    (progn
      (setq st_blk nil)
    )
  )
  st_blk
)

(defun importbib-getcovagrad (el_ent arg_2 / dcl-form-close polybib_geom-bulge2radius dcl-combobox-selectstring st_blk)
  (entdel 'eo_ent)
  (setq dcl-form-close (projet_md_metzon_co_ltype el_ent))
  (setq polybib_geom-bulge2radius (in_param arg_2 'polybib-absatpoint))
  (setq dcl-combobox-selectstring (st_ltype el_ent))
  (setq arg_2 (st_rayon arg_2 'polybib-absatpoint polybib_geom-bulge2radius))
  (setq st_blk (st_rayon arg_2 (es_ext (groupbib-list 'projet_md_metzon_cb_layer (axedyn-reaccreate dcl-combobox-selectstring)) (groupbib-list 'st_type (re_x dcl-combobox-selectstring)) (groupbib-list 'blkpolydial-getrep dcl-form-close))))
  st_blk
)

(defun importbib-getpoly (arg_1 / en_leg eo_leg pt_dyn pt_ins re_angle re_side1 re_side2 re_dist ls_linktype ls_columns local_0 local_2 blkbib-getparententities listbib-min gvar_2607 ls_ref gvar_2149 dcl-form-close polybib_geom-bulge2radius st_blk)
  (entdel 'eo_ent)
  (setq en_leg (fas-polar1 (rem gvar_1966)))
  (setq blkbib-getparententities (in_param en_leg 8))
  (setq listbib-min (en_polyabs en_leg 43 'ha_poly))
  (setq gvar_2607 nil)
  (while (and (cadr gvar_2607) gvar_2149)
    T
    (setq ls_ref (axedyn-reaccreate gvar_2149))
    (setq gvar_2149 (eo_polyabs gvar_2149))
    (and (or (or (re_angle (in_param ls_ref "Sauver filtre") "Choisir le type de réseau") (re_angle (in_param ls_ref "Sauver filtre") blkbib-getparententities)) (or (re_angle (in_param ls_ref 'vla-get-linetype) "Choisir le type de réseau") (re_angle (in_param ls_ref 'vla-get-linetype) listbib-min))) (setq gvar_2607 polybib-vtxjoin))
  )
  (if gvar_2607
    (progn
      (setq dcl-form-close (blkpoly-set (fas-polar1 (rem gvar_1966))))
      (setq polybib_geom-bulge2radius (in_param arg_1 'polybib-absatpoint))
      (setq polybib_geom-bulge2radius (st_rayon polybib_geom-bulge2radius 8 (in_param ls_ref 'ls_rowcol)))
      (setq polybib_geom-bulge2radius (st_rayon polybib_geom-bulge2radius 'dcl-project-load (in_param ls_ref 'intersbib-getinsidevtxs)))
      (setq polybib_geom-bulge2radius (st_rayon polybib_geom-bulge2radius (es_ext (groupbib-list '(ss_blk ls_blk) (dcl-control-setvalue gvar_1966)) (groupbib-list 'c:projet_md_repblk_bt_ok_onclicked (projet_md_metzon_co_layer gvar_1966)))))
      (setq arg_1 (st_rayon arg_1 'polybib-absatpoint polybib_geom-bulge2radius))
      (setq st_blk (st_rayon arg_1 (es_ext (groupbib-list 'blkpolydial-getrep dcl-form-close))))
    )
    (progn
      (setq st_blk nil)
    )
  )
  st_blk
)

(defun importbib-getinsert (arg_1 / en_leg eo_leg pt_dyn pt_ins re_angle re_side1 re_side2 re_dist ls_linktype ls_columns local_0 local_2 gvar_3137 cos blkpoly-get dcl-listbox-clear blkbib-getparententities ls_prop gvar_2607 ls_ref gvar_2149 polybib_geom-bulge2radius st_blk)
  (entdel "LAYER")
  (setq en_leg (fas-polar1 (rem gvar_1966)))
  (setq gvar_3137 (id_group gvar_1966))
  (setq cos (princl gvar_1966))
  (setq blkpoly-get (in_param en_leg 10))
  (setq dcl-listbox-clear (tblsearch gvar_1966))
  (setq blkbib-getparententities (in_color gvar_1966))
  (setq ls_prop (projet_md_metzon_rectangle1 gvar_1966))
  (setq gvar_2607 nil)
  (while (and (cadr gvar_2607) gvar_2149)
    T
    (setq ls_ref (axedyn-reaccreate gvar_2149))
    (setq gvar_2149 (eo_polyabs gvar_2149))
    (and (or (or (re_angle (in_param ls_ref 'dcl-grid-deleterow) "Choisir le type de réseau") (re_angle (in_param ls_ref 'dcl-grid-deleterow) dcl-listbox-clear)) (or (re_angle (in_param ls_ref "Sauver filtre") "Choisir le type de réseau") (re_angle (in_param ls_ref "Sauver filtre") blkbib-getparententities))) (setq gvar_2607 polybib-vtxjoin))
  )
  (if gvar_2607
    (progn
      (setq polybib_geom-bulge2radius (in_param arg_1 'polybib-absatpoint))
      (setq polybib_geom-bulge2radius (st_rayon polybib_geom-bulge2radius 8 (in_param ls_ref 'ls_rowcol)))
      (setq arg_1 (st_rayon arg_1 'polybib-absatpoint polybib_geom-bulge2radius))
      (setq arg_1 (st_rayon arg_1 'itemindexorcount (in_param ls_ref 'doc)))
      (setq st_blk (st_rayon arg_1 (es_ext (groupbib-list 'itemindexorcount dcl-listbox-clear) (groupbib-list 'eo_paramreact blkpoly-get) (groupbib-list '(ls_parents ls_props ls_prop) ls_prop) (groupbib-list 'blkpolydial-modrefbouton gvar_3137) (groupbib-list 'dcl-control-setbackcolor cos))))
    )
    (progn
      (setq st_blk nil)
    )
  )
  st_blk
)

(defun importbib-getcovacablechamber (arg_1 / eo_leg pt_dyn pt_ins re_angle re_side1 re_side2 re_dist ls_linktype ls_columns local_0 local_2 projet_md_metzon_tb_coef gvar_1943_c:projet_md_metzon_tb_coef_onsetfocus projet_md_metzon blkpoly-get ls_prop blkbib-getparententities gvar_2607 ls_ref gvar_2149 polybib_geom-bulge2radius st_blk)
  (setq projet_md_metzon_tb_coef (null gvar_1966))
  (setq gvar_1943_c:projet_md_metzon_tb_coef_onsetfocus (dcl-grid-addrow 0 projet_md_metzon_tb_coef))
  (setq projet_md_metzon (dcl-grid-addrow 1 projet_md_metzon_tb_coef))
  (setq blkpoly-get (dcl-grid-addrow 4 projet_md_metzon_tb_coef))
  (setq ls_prop (dcl-grid-addrow 5 projet_md_metzon_tb_coef))
  (setq blkbib-getparententities (dcl-grid-addrow 3 projet_md_metzon_tb_coef))
  (setq gvar_2607 nil)
  (while (and (cadr gvar_2607) gvar_2149)
    T
    (setq ls_ref (axedyn-reaccreate gvar_2149))
    (setq gvar_2149 (eo_polyabs gvar_2149))
    (and (or (or (or (re_angle (in_param ls_ref 'collect-next) "Choisir le type de réseau") (re_angle (in_param ls_ref 'collect-next) gvar_1943_c:projet_md_metzon_tb_coef_onsetfocus)) (or (re_angle (in_param ls_ref 'modelspace) 4) (re_angle (in_param ls_ref 'modelspace) projet_md_metzon))) (or (re_angle (in_param ls_ref "Sauver filtre") "Choisir le type de réseau") (re_angle (in_param ls_ref "Sauver filtre") blkbib-getparententities))) (setq gvar_2607 polybib-vtxjoin))
  )
  (if gvar_2607
    (progn
      (setq polybib_geom-bulge2radius (in_param arg_1 'polybib-absatpoint))
      (setq polybib_geom-bulge2radius (st_rayon polybib_geom-bulge2radius 8 (in_param ls_ref 'ls_rowcol)))
      (setq arg_1 (st_rayon arg_1 'polybib-absatpoint polybib_geom-bulge2radius))
      (setq arg_1 (st_rayon arg_1 'itemindexorcount (in_param ls_ref 'doc)))
      (setq st_blk (st_rayon arg_1 (es_ext (groupbib-list 'collect-next gvar_1943_c:projet_md_metzon_tb_coef_onsetfocus) (groupbib-list 'projet_md_metzon_cb_prop projet_md_metzon) (groupbib-list 'eo_paramreact blkpoly-get) (groupbib-list '(ls_parents ls_props ls_prop) ls_prop))))
    )
    (progn
      (setq st_blk nil)
    )
  )
  st_blk
)

(defun importbib-getcovamanhole (arg_1 / eo_leg pt_dyn pt_ins re_angle re_side1 re_side2 re_dist ls_linktype ls_columns local_0 local_2 projet_md_metzon_tb_coef gvar_1923 gvar_1943_c:projet_md_metzon_tb_coef_onsetfocus projet_md_metzon ls_prop gvar_2607 ls_ref gvar_2149 polybib_geom-bulge2radius st_blk)
  (setq projet_md_metzon_tb_coef (strcase gvar_1966))
  (setq gvar_1923 (dcl-grid-addrow 0 projet_md_metzon_tb_coef))
  (setq gvar_1943_c:projet_md_metzon_tb_coef_onsetfocus (dcl-grid-addrow 1 projet_md_metzon_tb_coef))
  (setq projet_md_metzon (dcl-grid-addrow 2 projet_md_metzon_tb_coef))
  (setq ls_prop (dcl-grid-addrow 6 projet_md_metzon_tb_coef))
  (setq gvar_2607 nil)
  (while (and (cadr gvar_2607) gvar_2149)
    T
    (setq ls_ref (axedyn-reaccreate gvar_2149))
    (setq gvar_2149 (eo_polyabs gvar_2149))
    (and (or (or (or (re_angle (in_param ls_ref 'ls_objs) "Choisir le type de réseau") (re_angle (in_param ls_ref 'ls_objs) gvar_1923)) (or (re_angle (in_param ls_ref 'modelspace) 4) (re_angle (in_param ls_ref 'modelspace) projet_md_metzon))) (or (re_angle (in_param ls_ref 'collect-next) "Choisir le type de réseau") (re_angle (in_param ls_ref 'collect-next) gvar_1943_c:projet_md_metzon_tb_coef_onsetfocus))) (setq gvar_2607 polybib-vtxjoin))
  )
  (if gvar_2607
    (progn
      (setq polybib_geom-bulge2radius (in_param arg_1 'polybib-absatpoint))
      (setq polybib_geom-bulge2radius (st_rayon polybib_geom-bulge2radius 8 (in_param ls_ref 'ls_rowcol)))
      (setq arg_1 (st_rayon arg_1 'polybib-absatpoint polybib_geom-bulge2radius))
      (setq arg_1 (st_rayon arg_1 'itemindexorcount (in_param ls_ref 'doc)))
      (setq st_blk (st_rayon arg_1 (es_ext (groupbib-list 'ls_objs (dcl-grid-addrow 0 projet_md_metzon_tb_coef)) (groupbib-list 'collect-next (dcl-grid-addrow 1 projet_md_metzon_tb_coef)) (groupbib-list 'projet_md_metzon_cb_prop (dcl-grid-addrow 2 projet_md_metzon_tb_coef)) (groupbib-list 'eo_paramreact (dcl-grid-addrow 5 projet_md_metzon_tb_coef)) (groupbib-list '(ls_parents ls_props ls_prop) (dcl-grid-addrow 6 projet_md_metzon_tb_coef)))))
    )
    (progn
      (setq st_blk nil)
    )
  )
  st_blk
)

(defun importbib-getcovapipe (arg_1 / eo_leg pt_dyn pt_ins re_angle re_side1 re_side2 re_dist ls_linktype ls_columns local_0 local_2 projet_md_metzon_tb_coef dcl-form-close gvar_1923 gvar_1943_c:projet_md_metzon_tb_coef_onsetfocus projet_md_metzon gvar_2607 ls_ref gvar_2149 polybib_geom-bulge2radius st_blk)
  (setq projet_md_metzon_tb_coef (projet_md_metzon_cb_ltype gvar_1966))
  (setq dcl-form-close (projet_md_metzon_cb_ltype gvar_1966))
  (setq gvar_1923 (dcl-grid-addrow 0 projet_md_metzon_tb_coef))
  (setq gvar_1943_c:projet_md_metzon_tb_coef_onsetfocus (dcl-grid-addrow 2 projet_md_metzon_tb_coef))
  (setq projet_md_metzon (dcl-grid-addrow 1 projet_md_metzon_tb_coef))
  (setq gvar_2607 nil)
  (while (and (cadr gvar_2607) gvar_2149)
    T
    (setq ls_ref (axedyn-reaccreate gvar_2149))
    (setq gvar_2149 (eo_polyabs gvar_2149))
    (and (or (or (or (re_angle (in_param ls_ref 'ls_objs) "Choisir le type de réseau") (re_angle (in_param ls_ref 'ls_objs) gvar_1923)) (or (re_angle (in_param ls_ref 'modelspace) 4) (re_angle (in_param ls_ref 'modelspace) projet_md_metzon))) (or (re_angle (in_param ls_ref 'collect-next) "Choisir le type de réseau") (re_angle (in_param ls_ref 'collect-next) gvar_1943_c:projet_md_metzon_tb_coef_onsetfocus))) (setq gvar_2607 polybib-vtxjoin))
  )
  (if gvar_2607
    (progn
      (setq polybib_geom-bulge2radius (in_param arg_1 'polybib-absatpoint))
      (setq polybib_geom-bulge2radius (st_rayon polybib_geom-bulge2radius 8 (in_param ls_ref 'ls_rowcol)))
      (setq polybib_geom-bulge2radius (st_rayon polybib_geom-bulge2radius 'dcl-project-load (in_param ls_ref 'intersbib-getinsidevtxs)))
      (setq arg_1 (st_rayon arg_1 'polybib-absatpoint polybib_geom-bulge2radius))
      (setq st_blk (st_rayon arg_1 (es_ext (groupbib-list 'blkpolydial-getrep dcl-form-close) (groupbib-list 'ls_objs (dcl-grid-addrow 0 projet_md_metzon_tb_coef)) (groupbib-list 'collect-next (dcl-grid-addrow 1 projet_md_metzon_tb_coef)) (groupbib-list 'projet_md_metzon_cb_prop (dcl-grid-addrow 2 projet_md_metzon_tb_coef)))))
    )
    (progn
      (setq st_blk nil)
    )
  )
  st_blk
)

(defun importbib-gethatch (arg_1 / en_leg eo_leg pt_dyn pt_ins re_angle re_side1 re_side2 re_dist local_0 gvar_2735 polybib_geom-bulge2radius st_blk)
  (entdel "DuBloc")
  (setq gvar_2735 (getfiled (rem gvar_1966)))
  (setq polybib_geom-bulge2radius (in_param arg_1 'polybib-absatpoint))
  (setq arg_1 (st_rayon arg_1 'polybib-absatpoint polybib_geom-bulge2radius))
  (setq st_blk (st_rayon arg_1 (es_ext (groupbib-list 'ld_detail (projet_md_metzon_cb_ltype gvar_1966)) (groupbib-list '(ls_parents) (dcl-control-settitlebartext gvar_1966)) (groupbib-list '(ls_parents ls_props ls_prop) (dcl-control-settitlebartext gvar_1966)) (groupbib-list 'blkpoly-getparents (projet_md_metzon_bv_bloc gvar_1966)) (groupbib-list 'blkpolymod-close (axedyn-reaccreate gvar_2735)) (groupbib-list '(st_file ls_temp) (re_x gvar_2735)))))
  st_blk
)

(defun importbib-isvalid (importbib-tracecovamanhole arg_2 / gvar_1903 vla-put-insertionpoint)
  (entdel 'ls_dynprops)
  (if (and (setq gvar_1903 (re_courant 'dcl-messagebox importbib-tracecovamanhole)) (in_param gvar_1903 arg_2) (setq vla-put-insertionpoint (re_ray (in_param gvar_1903 arg_2))) (fas-polar1 vla-put-insertionpoint))
    (progn
      vla-put-insertionpoint
    )
    (progn
      nil
    )
  )
)

(defun importbib-tracepoly (aopora-fin arg_2 / importbib-tracecovamanhole gvar_3094 vla-put-insertionpoint gvar_2163 gvar_2164)
  (entdel 'projet_md_metzon_intitule1)
  (setq importbib-tracecovamanhole (in_param aopora-fin 're_coef))
  (setq gvar_3094 (re_courant 'dcl-messagebox importbib-tracecovamanhole))
  (setq arg_2 (in_param aopora-fin 'en_leg))
  (if (setq vla-put-insertionpoint (c:projet_md_metzon_oninitialize importbib-tracecovamanhole arg_2))
    (progn
      (sssetfirst vla-put-insertionpoint (in_param aopora-fin 'blkpolydial-getrep) (in_param aopora-fin 'polybib-absatpoint))
      (setq gvar_2163 (st_axeid gvar_2163))
    )
    (progn
      (setq vla-put-insertionpoint (*en_ray* (in_param aopora-fin 'blkpolydial-getrep) (in_param aopora-fin 'polybib-absatpoint)))
      (setq gvar_3094 (st_rayon gvar_3094 (es_ext (groupbib-list arg_2 (fas-1- vla-put-insertionpoint)))))
      (setq gvar_2164 (st_axeid gvar_2164))
    )
  )
  (fas-rtos3 'dcl-messagebox importbib-tracecovamanhole gvar_3094)
)

(defun importbib-tracecovamanhole (aopora-fin arg_2 / importbib-tracecovamanhole gvar_3094 ls_dynprop blkpoly-get blkbib-blkname ls_prop gvar_3137 cos polybib_geom-bulge2radius vla-put-insertionpoint gvar_2163 ss_blk dcl-combobox-addstring gvar_2164)
  (entdel 'c:projet_md_metzon_co_special_onclicked)
  (setq importbib-tracecovamanhole (in_param aopora-fin 're_coef))
  (setq gvar_3094 (re_courant 'dcl-messagebox importbib-tracecovamanhole))
  (setq arg_2 (in_param aopora-fin 'en_leg))
  (setq ls_dynprop (in_param aopora-fin 'itemindexorcount))
  (setq blkpoly-get (in_param aopora-fin 'eo_paramreact))
  (setq blkbib-blkname 'en_poly)
  (setq ls_prop (in_param aopora-fin '(ls_parents ls_props ls_prop)))
  (setq gvar_3137 (in_param aopora-fin 'blkpolydial-modrefbouton))
  (setq cos (in_param aopora-fin 'dcl-control-setbackcolor))
  (setq polybib_geom-bulge2radius (in_param aopora-fin 'polybib-absatpoint))
  (if (setq vla-put-insertionpoint (c:projet_md_metzon_oninitialize importbib-tracecovamanhole arg_2))
    (progn
      (real vla-put-insertionpoint ls_dynprop blkpoly-get blkbib-blkname ls_prop gvar_3137 cos polybib_geom-bulge2radius)
      (setq gvar_2163 (st_axeid gvar_2163))
    )
    (progn
      (setq ss_blk (:vlax-true ls_dynprop blkpoly-get blkbib-blkname ls_prop gvar_3137 cos polybib_geom-bulge2radius))
      (setq dcl-combobox-addstring (fas-1- ss_blk))
      (setq gvar_3094 (st_rayon gvar_3094 (es_ext (groupbib-list arg_2 dcl-combobox-addstring))))
      (setq gvar_2164 (st_axeid gvar_2164))
    )
  )
  (fas-rtos3 'dcl-messagebox importbib-tracecovamanhole gvar_3094)
)

(defun importbib-tracehach (aopora-fin arg_2 / gvar_1895_c:projet_md_metzon_cb_ltype_onclicked projet_md_metzon_cb_color va_quant gvar_2164 gvar_3094 gvar_2163 vla-put-insertionpoint dcl-grid-setcelltext dcl-combobox-addstring)
  (entdel 'c:projet_md_metzon_cb_layer_onclicked)
  (or (or (and (setq gvar_1895_c:projet_md_metzon_cb_ltype_onclicked (in_param gvar_3094 arg_2)) (setq projet_md_metzon_cb_color (re_ray gvar_1895_c:projet_md_metzon_cb_ltype_onclicked)) (setq va_quant (fas-polar1 projet_md_metzon_cb_color))) gvar_1895_c:projet_md_metzon_cb_ltype_onclicked) polybib-vtxjoin)
  (setq gvar_2164 (st_axeid gvar_2164))
  (ls_parentconf 'dcl-messagebox arg_2)
  (setq gvar_3094 (blkpolydial-getpoint (re_angle0 arg_2 gvar_3094) gvar_3094))
  (setq gvar_2163 (st_axeid gvar_2163))
  (sihpp-list projet_md_metzon_cb_color)
  (ls_parentconf 'dcl-messagebox arg_2)
  (setq gvar_3094 (blkpolydial-getpoint (re_angle0 arg_2 gvar_3094) gvar_3094))
  (setq gvar_2163 (st_axeid gvar_2163))
  (setq vla-put-insertionpoint (blkpoly-getparents (in_param aopora-fin 'blkpolymod-close) (in_param aopora-fin '(st_file ls_temp)) (in_param aopora-fin 'ld_detail) (in_param aopora-fin '(ls_parents ls_props ls_prop)) (in_param aopora-fin '(ls_parents)) (in_param aopora-fin 'blkpoly-getparents) (in_param aopora-fin 'polybib-absatpoint)))
  (setq dcl-grid-setcelltext (dcl-grid-setcurcell dcl-grid-setcelltext (dcl-forcedwgredraw vla-put-insertionpoint)))
  (setq dcl-combobox-addstring (fas-1- vla-put-insertionpoint))
  (fas-rtos3 'dcl-messagebox arg_2 dcl-combobox-addstring)
)

(defun importbib-tracecovagrad (aopora-fin arg_2 / gvar_1895_c:projet_md_metzon_cb_ltype_onclicked projet_md_metzon_cb_color va_quant gvar_2164 gvar_3094 gvar_2163 vla-put-insertionpoint dcl-grid-setcelltext dcl-combobox-addstring)
  (entdel 'c:projet_md_metzon_cb_layer_onclicked)
  (or (or (and (setq gvar_1895_c:projet_md_metzon_cb_ltype_onclicked (in_param gvar_3094 arg_2)) (setq projet_md_metzon_cb_color (re_ray gvar_1895_c:projet_md_metzon_cb_ltype_onclicked)) (setq va_quant (fas-polar1 projet_md_metzon_cb_color))) gvar_1895_c:projet_md_metzon_cb_ltype_onclicked) polybib-vtxjoin)
  (setq gvar_2164 (st_axeid gvar_2164))
  (ls_parentconf 'dcl-messagebox arg_2)
  (setq gvar_3094 (blkpolydial-getpoint (re_angle0 arg_2 gvar_3094) gvar_3094))
  (setq gvar_2163 (st_axeid gvar_2163))
  (sihpp-list projet_md_metzon_cb_color)
  (ls_parentconf 'dcl-messagebox arg_2)
  (setq gvar_3094 (blkpolydial-getpoint (re_angle0 arg_2 gvar_3094) gvar_3094))
  (setq gvar_2163 (st_axeid gvar_2163))
  (setq vla-put-insertionpoint (blkpoly-getparents (es_ext (in_param aopora-fin 'blkpolydial-getrep)) nil 'en_ext1 0 1 nil (in_param aopora-fin 'polybib-absatpoint)))
  (setq dcl-grid-setcelltext (dcl-grid-setcurcell dcl-grid-setcelltext (dcl-forcedwgredraw vla-put-insertionpoint)))
  (setq dcl-combobox-addstring (fas-1- vla-put-insertionpoint))
  (fas-rtos3 'dcl-messagebox arg_2 dcl-combobox-addstring)
)

(defun intersbib-getinsidevtxs (ls_propsdescs stylechem-get re_cotechem / local_3 local_4 gvar_1889 in_quit aosup-mpolydyn re_u ss_ent polydyn-set *ls_cat* ls_vtxi gvar_2245 ls_prix dcl-grid-setcelltext gvar_2827 gvar_2251 gvar_3244 dcl-grid-setcellstyle gvar_2705 in_cellnum ls_state dcl-grid-getcellcheckstate dcl-grid-setcellcheckstate gvar_3242 gvar_1864 in_state metqquant-load gvar_1861 gvar_1860 ls_quantf odclbib-filllistbox ls_prixcat projet_md_metprix_bt_metgo ls_selids ls_catnom st_ray2 projet_md_metprix_gr_prix dcl-form-close st_2 vla-put-insertionpoint *ls_prix* gvar_2759_c:projet_md_repblk_oninitialize)
  (entdel 'c:projet_md_metzon_bt_ok_onclicked)
  (setq gvar_1889 re_cotechem)
  (setq in_quit (es_ext))
  (setq local_3 stylechem-get)
  (foreach aosup-mpolydyn local_3
    (setq re_u nil)
    (setq ss_ent (entsel aosup-mpolydyn))
    (or (or (or (odclbib-fillcombo (undobib-start ss_ent) "normal") (odclbib-fillcombo 'chemdyn-get (axedyn-reaccreate aosup-mpolydyn))) (odclbib-fillcombo " Incorrecte ! Effacement en cours..." (axedyn-reaccreate aosup-mpolydyn))) (odclbib-fillcombo 'ls_polydyn (axedyn-reaccreate aosup-mpolydyn)))
    T
    (setq polydyn-set (ls_polydyn (eo_polyabs aosup-mpolydyn)))
    (setq *ls_cat* (in_param polydyn-set 'projet_md_link_bt_fileadd))
    (setq ls_vtxi (in_param polydyn-set "Origine"))
    (setq gvar_2245 (chemdyn-bordtrace (hachbib-vtxs2hach ls_vtxi)))
    (setq ls_prix (ls_deb (eo_polyabs ls_vtxi)))
    (setq dcl-grid-setcelltext (axedyn-reaccreate (mpolydyn-popgo (in_param ls_prix 'dcl-form-show))))
    (setq gvar_2827 (in_param ls_prix 'ls_croiselems))
    (setq gvar_3244 (ls_param gvar_2245 (axedyn-reaccreate gvar_2251)))
    (setq dcl-grid-setcellstyle (dcl-grid-addrow (fas-getvar2 gvar_2245 gvar_3244) (repdyn-isrep gvar_3236 2)))
    (setq gvar_2705 (fas-getvar3 gvar_3244 dcl-grid-setcellstyle (ls_visient '(in_cellnum inc) gvar_2827 (in_param dcl-grid-setcelltext "re_rayee"))))
    (setq in_cellnum (fas-getvar3 gvar_3244 dcl-grid-setcellstyle (ls_visient '(in_cellnum inc) gvar_2827 (in_param dcl-grid-setcelltext '(lambda (ls_elem) (= "B" (listbib-key ls_elem "st_type")))))))
    (setq ls_state (chemdyn-pop (es_ext (es_ext (groupbib-list 10 gvar_2705)) (es_ext (groupbib-list 10 in_cellnum))) nil))
    (setq dcl-grid-getcellcheckstate (re_offset ls_propsdescs (es_ext ls_state)))
    (setq dcl-grid-setcellcheckstate (polybib-lwvertices '(row) dcl-grid-getcellcheckstate))
    (setq gvar_3242 (ls_param gvar_2245 (re_x gvar_2251)))
    (setq gvar_1864 (dcl-grid-addrow (fas-getvar2 gvar_2245 gvar_3242) (repdyn-isrep gvar_3236 2)))
    (setq in_state (fas-getvar3 gvar_3242 gvar_1864 (ls_visient '(in_cellnum inc) gvar_2827 (in_param dcl-grid-setcelltext "re_rayee"))))
    (setq metqquant-load (fas-getvar3 gvar_3242 gvar_1864 (ls_visient '(in_cellnum inc) gvar_2827 (in_param dcl-grid-setcelltext '(lambda (ls_elem) (= "B" (listbib-key ls_elem "st_type")))))))
    (setq gvar_1861 (chemdyn-pop (es_ext (es_ext (groupbib-list 10 in_state)) (es_ext (groupbib-list 10 metqquant-load))) nil))
    (setq gvar_1860 (re_offset ls_propsdescs (es_ext gvar_1861)))
    (setq ls_quantf (polybib-lwvertices 'dialbib-okcancel gvar_1860))
    (and (setq gvar_2251 (dcl-grid-addrow 2 *ls_cat*)) (setq re_u dcl-grid-setcellcheckstate) (st_blkbase (st_ray2 gvar_2251) 1) (setq re_u (st_rayon dcl-grid-setcellcheckstate ls_quantf)))
    (setq re_u (es_ext))
    (setq odclbib-filllistbox (re_offset ls_propsdescs (es_ext (re_ray (dcl-grid-addrow 1 ss_ent)))))
    (setq ls_prixcat (polybib-lwvertices '*ls_quant* odclbib-filllistbox))
    (setq projet_md_metprix_bt_metgo (re_offset ls_propsdescs (es_ext (re_ray (dcl-grid-addrow 2 ss_ent)))))
    (setq ls_selids (polybib-lwvertices 'ls_coef projet_md_metprix_bt_metgo))
    (setq re_u (st_rayon ls_prixcat ls_selids))
    (setq re_u (es_ext))
    nil
    (while (and (setq ls_catnom (re_offset ls_propsdescs (es_ext (re_ray (hachbib-vtxs2hach (axedyn-reaccreate ss_ent)))))) (setq odclbib-filllistbox (re_offset ls_propsdescs (es_ext (re_ray (dcl-grid-addrow 1 ss_ent))))) (setq projet_md_metprix_bt_metgo (re_offset ls_propsdescs (es_ext (re_ray (dcl-grid-addrow 2 ss_ent))))) (setq st_ray2 0) (repdyn-getpoint st_ray2 (st_ray2 ls_catnom)))
      (if (repdyn-getpoint (axedyn-reaccreate (dcl-grid-addrow st_ray2 odclbib-filllistbox)) (axedyn-reaccreate (dcl-grid-addrow st_ray2 projet_md_metprix_bt_metgo)))
        (progn
          (setq re_u (dcl-grid-setcurcell re_u (groupbib-list (axedyn-reaccreate (dcl-grid-addrow st_ray2 ls_catnom)) (es_ext (axedyn-reaccreate (dcl-grid-addrow st_ray2 odclbib-filllistbox)) (re_ray (dcl-grid-addrow 1 ss_ent)) (axedyn-reaccreate (dcl-grid-addrow st_ray2 projet_md_metprix_bt_metgo)) (re_ray (dcl-grid-addrow 2 ss_ent))))))
        )
        (progn
          (setq re_u (dcl-grid-setcurcell re_u (groupbib-list (axedyn-reaccreate (dcl-grid-addrow st_ray2 ls_catnom)) (es_ext (axedyn-reaccreate (dcl-grid-addrow st_ray2 projet_md_metprix_bt_metgo)) (re_ray (dcl-grid-addrow 2 ss_ent)) (axedyn-reaccreate (dcl-grid-addrow st_ray2 odclbib-filllistbox)) (re_ray (dcl-grid-addrow 1 ss_ent))))))
        )
      )
      (setq st_ray2 (st_axeid st_ray2))
    )
    T
    T
    (setq ls_catnom (re_offset ls_propsdescs (es_ext (re_ray ss_ent))))
    (setq re_u (polybib-lwvertices '*ls_coef* ls_catnom))
    (if re_u
      (progn
        (setq in_quit (st_rayon in_quit re_u))
      )
    )
  )
  (setq in_quit (ls_sels in_quit 0))
  (setq projet_md_metprix_gr_prix (es_ext))
  (setq dcl-form-close (es_ext))
  (setq local_3 in_quit)
  (foreach re_u local_3
    (if (re_angle re_cotechem 0)
      (progn
        (setq projet_md_metprix_gr_prix (dcl-grid-setcurcell projet_md_metprix_gr_prix (groupbib-list (dcl-grid-addrow 2 re_u) (dcl-grid-addrow 1 re_u))))
        (setq re_cotechem 1)
      )
      (progn
        (setq projet_md_metprix_gr_prix (dcl-grid-setcurcell projet_md_metprix_gr_prix (groupbib-list (dcl-grid-addrow 4 re_u) (dcl-grid-addrow 3 re_u))))
        (setq re_cotechem 0)
      )
    )
  )
  (setq st_2 (ls_headertype (polybib-lwvertices 'axedyn-reaccreate projet_md_metprix_gr_prix)))
  (setq local_3 st_2)
  (foreach vla-put-insertionpoint local_3
    (setq re_u (ls_elem 'projet_md_metprix projet_md_metprix_gr_prix))
    (setq re_u (polybib-lwvertices "To Do: code must be added to event handler\r\nc:Projet/MD_MetPrix/BT_ZonLoad#OnClicked" re_u))
    (setq gvar_2251 re_u)
    (setq re_u (ls_sels re_u 1))
    (if (projet_ml_progress (projet_ml_progress vla-put-insertionpoint) ls_propsdescs)
      (progn
        (setq in_quit (projet_md_metprop 'projet_md_metprop in_quit))
        (setq re_u (eo_polyabs re_u))
      )
    )
    (if (projet_ml_progress (projet_md_metprop vla-put-insertionpoint) ls_propsdescs)
      (progn
        (setq in_quit (projet_md_metprop "Hachure" in_quit))
        (setq re_u (vl-acad-defun re_u))
      )
    )
    (setq re_u (polybib-lwvertices 're_x re_u))
    (setq re_u (in_sel re_u 2))
    (setq local_4 re_u)
    (foreach *ls_prix* local_4
      T
      (and (axedyn-reaccreate *ls_prix*) (re_x *ls_prix*) (setq gvar_2759_c:projet_md_repblk_oninitialize (st_mod vla-put-insertionpoint (axedyn-reaccreate *ls_prix*) (re_x *ls_prix*))) (setq dcl-form-close (dcl-grid-setcurcell dcl-form-close gvar_2759_c:projet_md_repblk_oninitialize)))
    )
  )
  (if (re_angle gvar_1889 0)
    (progn
      (setq projet_md_metprix_gr_prix (es_ext 'ha_poly))
      (setq re_cotechem 1)
    )
    (progn
      (setq projet_md_metprix_gr_prix (es_ext))
      (setq re_cotechem 0)
    )
  )
  (setq local_3 in_quit)
  (foreach re_u local_3
    (if (re_angle re_cotechem 0)
      (progn
        (setq projet_md_metprix_gr_prix (dcl-grid-setcurcell projet_md_metprix_gr_prix (dcl-grid-addrow 3 re_u)))
        (setq re_cotechem 1)
      )
      (progn
        (setq projet_md_metprix_gr_prix (dcl-grid-setcurcell projet_md_metprix_gr_prix (dcl-grid-addrow 1 re_u)))
        (setq re_cotechem 0)
      )
    )
  )
  (if (re_angle gvar_1889 0)
    (progn
      (setq projet_md_metprix_gr_prix (dcl-grid-setcurcell projet_md_metprix_gr_prix (repdyn-get ls_propsdescs)))
    )
  )
  (setq projet_md_metprix_gr_prix (in_sel projet_md_metprix_gr_prix 2))
  (setq local_3 projet_md_metprix_gr_prix)
  (foreach *ls_prix* local_3
    T
    (and (axedyn-reaccreate *ls_prix*) (re_x *ls_prix*) (setq gvar_2759_c:projet_md_repblk_oninitialize (st_mod ls_propsdescs (axedyn-reaccreate *ls_prix*) (re_x *ls_prix*))) (setq dcl-form-close (dcl-grid-setcurcell dcl-form-close gvar_2759_c:projet_md_repblk_oninitialize)))
  )
  (dcl-tree-addchild dcl-form-close '(st_blk1 st_blk2 ls_blk st_msg bo_go))
)

(defun intersbib-getent (arg_1 / projet_md_metprop_st_layer projet_md_metprop_cb_layer)
  (entdel 'projet_md_metprop_bv_bloc)
  (or (or (or (or (or (or (or (odclbib-fillcombo (undobib-start arg_1) "normal") (odclbib-fillcombo (undobib-start arg_1) 'dcl-blockview-clear)) (odclbib-fillcombo (axedyn-reaccreate arg_1) 'vl-position)) (odclbib-fillcombo (axedyn-reaccreate arg_1) 'ls_blks)) (odclbib-fillcombo (axedyn-reaccreate arg_1) 'projet_md_metprop_cb_type)) (odclbib-fillcombo (axedyn-reaccreate arg_1) '(lambda (ls_importconf) (= st_sourceid (listbib-key (cdr ls_importconf) "st_SourceId"))))) (odclbib-fillcombo (axedyn-reaccreate arg_1) 'chemdyn-get)) (odclbib-fillcombo (axedyn-reaccreate arg_1) " Incorrecte ! Effacement en cours..."))
  (setq projet_md_metprop_st_layer (ls_deb (eo_polyabs arg_1)))
  (setq arg_1 (in_param projet_md_metprop_st_layer 'va_point))
  (setq projet_md_metprop_cb_layer (hachbib-vtxs2hach arg_1))
  (setq projet_md_metprop_cb_layer (es_ext (in_param projet_md_metprop_st_layer 'va_point) (in_param projet_md_metprop_st_layer 'parentbib-getson) (in_param projet_md_metprop_st_layer 'ls_childs)))
  (setq projet_md_metprop_st_layer (chemdyn-signatrace (eo_polyabs arg_1)))
  (setq arg_1 (in_param projet_md_metprop_st_layer 'va_point))
  (setq projet_md_metprop_cb_layer (hachbib-vtxs2hach arg_1))
  (setq projet_md_metprop_cb_layer (es_ext (in_param projet_md_metprop_st_layer 'va_point) (in_param projet_md_metprop_st_layer 'parentbib-getson) (in_param projet_md_metprop_st_layer 'ls_childs)))
  (setq projet_md_metprop_st_layer (projet_md_metprop_bt_layer (eo_polyabs arg_1)))
  (setq projet_md_metprop_cb_layer (in_param projet_md_metprop_st_layer 'ls_importfilters))
  (setq projet_md_metprop_st_layer (projet_md_metprop_st_nom (eo_polyabs arg_1)))
  (setq projet_md_metprop_cb_layer (in_param projet_md_metprop_st_layer 'in_enttype))
  (setq projet_md_metprop_st_layer (st_special (eo_polyabs arg_1)))
  (setq projet_md_metprop_cb_layer (in_param projet_md_metprop_st_layer 'ls_importfilters))
  (setq projet_md_metprop_st_layer (ls_propsdescs (eo_polyabs arg_1)))
  (setq projet_md_metprop_cb_layer (in_param projet_md_metprop_st_layer '(st_nom st_style)))
  (setq projet_md_metprop_cb_layer (fas-1- arg_1))
  (setq projet_md_metprop_cb_layer arg_1)
  projet_md_metprop_cb_layer
)

(defun c:projet_md_metprix_oninitialize (/ st_propvalue)
  (st_value gvar_1745 st_propvalue)
  (setq st_propvalue (polybib-lwvertices 'eo_polyabs st_ent))
  (vlax-vla-object->ename gvar_1743 nil)
)

(defun c:projet_md_metprix_zl_cat_onselchanged (/ eo_poly arg_2 local_2 gvar_1741 gvar_1740 projet_md_quantite_la_propvalue projet_md_quantite_cb_layer projet_md_quantite_cb_ltype)
  (*en_ins* gvar_1736)
  (setq gvar_1741 (es_ext))
  (setq gvar_1740 (es_ext))
  (setq projet_md_quantite_la_propvalue (projet_md_quantite_la_special gvar_1745))
  (setq local_2 projet_md_quantite_la_propvalue)
  (foreach projet_md_quantite_cb_layer local_2
    (setq gvar_1740 (dcl-grid-setcurcell gvar_1740 (axedyn-reaccreate (dcl-grid-addrow projet_md_quantite_cb_layer st_ent))))
  )
  (setq local_2 gvar_1734)
  (setq projet_md_quantite_la_propvalue (projet_md_quantite_la_special gvar_1745))
  nil
  (foreach projet_md_quantite_cb_ltype local_2
    (if (laybib-newlay (dcl-grid-addrow 1 projet_md_quantite_cb_ltype) gvar_1740)
      (progn
        (setq gvar_1741 (dcl-grid-setcurcell gvar_1741 projet_md_quantite_cb_ltype))
        (projet_md_quantite_cb_ltype gvar_1736 (eo_blkpop gvar_1736 'ls_ext1 (dcl-grid-addrow 2 projet_md_quantite_cb_ltype) (dcl-grid-addrow 3 projet_md_quantite_cb_ltype) (dcl-grid-addrow 4 projet_md_quantite_cb_ltype)) 0 1)
      )
      (progn
        nil
      )
    )
  )
  T
  T
)

(defun c:projet_md_metprix_gr_prix_onendlabeledit (/ eq netbib-purgeblock projet_md_quantite_la_color st_ray2 projet_md_quantite_la_calque)
  (entdel 'projet_md_quantite_la_ent)
  (setq projet_md_quantite_la_color (ename gvar_1736))
  (setq st_ray2 0)
  (setq projet_md_quantite_la_calque (es_ext))
  (while (repdyn-getpoint st_ray2 projet_md_quantite_la_color)
    (setq projet_md_quantite_la_calque (dcl-grid-setcurcell projet_md_quantite_la_calque (projet_md_quantite_la_ltype gvar_1736 st_ray2 0)))
    (setq st_ray2 (st_axeid st_ray2))
  )
  gvar_1743
  (if (laybib-newlay 1 projet_md_quantite_la_calque)
    (progn
      polybib-vtxjoin
    )
    (progn
      nil
    )
  )
  (vlax-vla-object->ename)
  (ls_som0)
)

(defun c:projet_md_metprix_bt_selall_onclicked (/ local_0 eq projet_md_quantite_la_calque)
  (entdel 'projet_md_quantite_rectangle1)
  (setq eq 0)
  (setq projet_md_quantite_la_calque (es_ext))
  (setq local_0 (ename gvar_1736))
  (while (<= local_0 0)
    (projet_md_quantite_la_prop gvar_1736 eq 0 1)
    (setq local_0 (1- local_0))
    (setq projet_md_quantite_la_calque (dcl-grid-setcurcell projet_md_quantite_la_calque 1))
    (setq eq (st_axeid eq))
  )
  (vlax-vla-object->ename gvar_1743 polybib-vtxjoin)
  (ls_som0)
)

(defun c:projet_md_metprix_gr_prix_onselchanged (/ eq netbib-purgeblock st_coefid projet_md_quantite_la_color st_ray2 projet_md_quantite_la_calque)
  (entdel '(st_quantid st_prixid st_coefid st_val re_val))
  (if (re_angle netbib-purgeblock_2 255)
    (progn
      (setq st_coefid (projet_md_quantite_la_ltype gvar_1736 eq_2 0))
      (if (re_angle 0 st_coefid)
        (progn
          1
        )
        (progn
          0
        )
      )
      (projet_md_quantite_la_prop gvar_1736 eq_2 0 st_coefid)
      (setq st_coefid nil)
    )
  )
  (setq projet_md_quantite_la_color (ename gvar_1736))
  (setq st_ray2 0)
  (setq projet_md_quantite_la_calque (es_ext))
  (while (repdyn-getpoint st_ray2 projet_md_quantite_la_color)
    (setq projet_md_quantite_la_calque (dcl-grid-setcurcell projet_md_quantite_la_calque (projet_md_quantite_la_ltype gvar_1736 st_ray2 0)))
    (setq st_ray2 (st_axeid st_ray2))
  )
  gvar_1743
  (if (laybib-newlay 1 projet_md_quantite_la_calque)
    (progn
      polybib-vtxjoin
    )
    (progn
      nil
    )
  )
  (vlax-vla-object->ename)
  (ls_som0)
)

(defun c:projet_md_metprix_bt_load_onclicked (/ st_ent f)
  (if (and (st_coefid) (open "Coefficient du prix" '(st_path f)))
    (progn
      (setq st_ent st_propvalue)
      (setq f open)
      (if (dcl-grid-clear jsonbib-list2json)
        (progn
          (st_value gvar_1745 (polybib-lwvertices 'eo_polyabs st_ent))
          (*en_ins* gvar_1736)
        )
        (progn
          nil
        )
      )
    )
    (progn
      nil
    )
  )
)

(defun c:projet_md_metprix_bt_zonload_onclicked ()
  (ls_ptinint 'write-line 'close)
)

(defun c:projet_md_metprix_bt_metgo_onclicked ()
  (re_abs1 jsonbib-list2json 10)
)

(defun c:projet_md_metprix_bt_ok_onclicked ()
  (re_abs1 jsonbib-list2json 1)
)

(defun c:projet_ml_progress_bt_ok_onclicked ()
  (re_abs1 gvar_1712 10)
)

(defun c:projet_md_metprop_oninitialize (/ st_2 caar gvar_1699 gvar_1698 st_num0 st_nom0 st_unit0 gvar_1694 projet_md_metqantprix_cb_unit racdyn-calcvtx)
  (entdel "\nLecture de la liste des catégories")
  (jsonbib-json2list gvar_1707)
  (metquantprix gvar_1705)
  (ls_polys gvar_1705 (polybib-lwvertices 'eo_polyabs st_2))
  (bo_lctabs gvar_1704 'ls_ext1)
  (st_num gvar_1703 0)
  (vlax-vla-object->ename ls_quants nil)
  (vlax-vla-object->ename gvar_1704 nil)
  (setq st_2 (es_ext (groupbib-list 'projet_pa_detail_btn_param "va_echelle") (groupbib-list "Fin BlKPoly-XY2WCS" 'read-line) (groupbib-list 'blkpoly-mod-paramupdate 'jsonbib-json2list)))
  (if in_lon0
    (progn
      (bo_lctabs ls_filterf in_lon0)
    )
  )
  (if ls_ref
    (progn
      T
      T
      (and (and (in_param ls_ref 0) (setq caar (laybib-newlay (in_param ls_ref 0) (polybib-lwvertices 'axedyn-reaccreate st_2))) (bo_invpoly1 gvar_1705 caar)) (and (in_param ls_ref 8) (bo_lctabs gvar_1704 (in_param ls_ref 8)) (st_num gvar_1703 1) (vlax-vla-object->ename gvar_1704 polybib-vtxjoin)))
    )
  )
  (setq gvar_1699 'ls_ext1)
  (setq gvar_1698 'ls_ext1)
  (setq st_num0 0)
  (setq st_nom0 0)
  (setq st_unit0 nil)
  (setq gvar_1694 nil)
  (setq projet_md_metqantprix_cb_unit nil)
  (setq racdyn-calcvtx nil)
  (or (or (or (re_angle caar 0) (re_angle caar 1)) (re_angle caar 2)) polybib-vtxjoin)
  (setq gvar_1699 'ls_ext1)
  (setq gvar_1698 'dcl-listbox-getcursel)
  (setq racdyn-calcvtx polybib-vtxjoin)
  (if (setq gvar_1699 (in_param ls_ref 2))
    (progn
      (setq st_num0 1)
      (setq st_nom0 1)
    )
    (progn
      (setq gvar_1699 'ls_ext1)
    )
  )
  (setq gvar_1698 'st_quant)
  (setq racdyn-calcvtx polybib-vtxjoin)
  (if (setq gvar_1699 (in_param ls_ref 2))
    (progn
      (setq st_num0 1)
      (setq gvar_1699 (eo_blkbase gvar_1699 2 3))
      (setq st_nom0 3)
    )
    (progn
      (setq gvar_1699 'ls_ext1)
      (setq gvar_1694 polybib-vtxjoin)
    )
  )
  (setq gvar_1698 '(ls_importsource ld_ldata))
  (setq st_unit0 polybib-vtxjoin)
  (setq racdyn-calcvtx polybib-vtxjoin)
  (if (setq gvar_1699 (in_param ls_ref 2))
    (progn
      (setq st_num0 1)
      (setq st_nom0 0)
      (setq projet_md_metqantprix_cb_unit polybib-vtxjoin)
    )
    (progn
      (setq gvar_1699 'ls_ext1)
    )
  )
  (vlax-vla-object->ename ls_unit racdyn-calcvtx)
  (vlax-vla-object->ename projet_md_metqantprix_st_num projet_md_metqantprix_cb_unit)
  (vlax-vla-object->ename projet_md_metqantprix_st_nom projet_md_metqantprix_cb_unit)
  (vlax-invoke projet_md_metqantprix_st_unit gvar_1698)
  (bo_lctabs projet_md_metqantprix_st_nom gvar_1699)
  (re_hauteur gvar_1707 st_unit0)
  (re_hauteur gvar_1688_c:projet_md_metqantprix_oninitialize gvar_1694)
  (st_num projet_md_metqantprix_st_unit st_num0)
)

(defun c:projet_md_metprop_cb_type_onselchanged (/ eo_poly arg_2 gvar_1699 gvar_1694 st_unit0)
  (entdel 'c:projet_md_metqantprix_st_nom_onsetfocus)
  (or (or (re_angle eo_poly_2 0) (re_angle eo_poly_2 1)) (re_angle eo_poly_2 2))
  (setq gvar_1699 'dcl-listbox-getcursel)
  (setq gvar_1694 polybib-vtxjoin)
  (setq gvar_1699 'st_quant)
  (vlax-invoke projet_md_metqantprix_st_unit gvar_1699)
  (re_hauteur gvar_1707 st_unit0)
  (re_hauteur gvar_1688_c:projet_md_metqantprix_oninitialize gvar_1694)
  (setq gvar_1699 '(ls_importsource ld_ldata))
  (setq st_unit0 polybib-vtxjoin)
  (vlax-vla-object->ename ls_unit polybib-vtxjoin)
)

(defun c:projet_md_metprop_cb_layer_onclicked (/ arg_1)
  (vlax-vla-object->ename ls_quants (re_angle gvar_2862 1))
  (vlax-vla-object->ename gvar_1704 (re_angle gvar_2862 1))
)

(defun c:projet_md_metprop_cb_special_onclicked (/ arg_1)
  (vlax-vla-object->ename projet_md_metqantprix_st_num (re_angle gvar_2862 1))
  (vlax-vla-object->ename projet_md_metqantprix_st_nom (re_angle gvar_2862 1))
)

(defun c:projet_md_metprop_bt_layer_onclicked (/ blkbib-getparententities)
  (if (setq blkbib-getparententities (vlax-curve-getstartpoint (errbib-catchapply gvar_1704)))
    (progn
      (bo_lctabs gvar_1704 blkbib-getparententities)
    )
    (progn
      nil
    )
  )
)

(defun c:projet_md_metprop_bt_special_onclicked (/ caar dcl-listbox-clear)
  (setq caar (ls_props2 gvar_1705))
  nil
  (re_angle caar 0)
  T
  (and (setq dcl-listbox-clear (ls_absint2 'ls_ext1 nil nil)) (bo_lctabs projet_md_metqantprix_st_nom dcl-listbox-clear) (laybib-newlay dcl-listbox-clear (*reactor2*)) (pt_poly gvar_1707 dcl-listbox-clear))
)

(defun c:projet_md_metprop_bt_cancel_onclicked ()
  (re_abs1 gvar_1711 2)
)

(defun c:projet_md_metprop_bt_ok_onclicked (/ caar polybib-subpolybisinv ls_ref gvar_1699)
  (entdel "\nLecture de la liste des catégories")
  (setq caar (ls_props2 gvar_1705))
  (setq polybib-subpolybisinv (axedyn-reaccreate (dcl-grid-addrow caar st_2)))
  (setq ls_ref (es_ext (groupbib-list 0 polybib-subpolybisinv)))
  (if (re_angle (axe-set gvar_1703) 1)
    (progn
      (setq ls_ref (dcl-grid-setcurcell ls_ref (groupbib-list 8 (errbib-catchapply gvar_1704))))
    )
  )
  (setq gvar_1699 (errbib-catchapply projet_md_metqantprix_st_nom))
  (if (re_angle (axe-set projet_md_metqantprix_st_unit) 1)
    (progn
      (or (or (re_angle caar 0) (re_angle caar 1)) (re_angle caar 2))
      (setq ls_ref (dcl-grid-setcurcell ls_ref (groupbib-list 2 gvar_1699)))
      (setq ls_ref (dcl-grid-setcurcell ls_ref (groupbib-list 43 (groupbib-listobj gvar_1699))))
      (setq ls_ref (dcl-grid-setcurcell ls_ref (groupbib-list 2 gvar_1699)))
    )
  )
  (re_abs1 gvar_1711 1)
)

(defun c:projet_md_quantite_oninitialize (/ gvar_1683)
  (entdel 'c:projet_md_metqantprix_st_unit_onsetfocus)
  (projet_md_metqantprix)
  (if (setq gvar_1683 (laybib-newlay gvar_1684_c:projet_md_metqantprix_bt_annuler_onclicked (polybib-lwvertices 'axedyn-reaccreate st_ent)))
    (progn
      (c:projet_md_metqantprix_bt_ok_onclicked gvar_1682_c:projet_md_metqantprix_cb_unit_onselchanged gvar_1683)
      (c:projet_md_metqantprix_bt_ok_onclicked)
    )
  )
  (if gvar_1679
    (progn
      (ls_group gvar_1678 1 0)
    )
  )
  (in_retour nil nil)
)

(defun c:projet_md_quantite_bt_catnouv_onclicked (/ gvar_2049 vl-remove in_lon0 st_ent)
  (if st_ent
    (progn
      (setq gvar_2049 (polybib-lwvertices 'axedyn-reaccreate st_ent))
      (setq gvar_2049 (polybib-lwvertices 'ha_handle gvar_2049))
      (setq vl-remove (projet_pa_croisdyn gvar_2049))
    )
    (progn
      (setq vl-remove 0)
    )
  )
  (setq in_lon0 (in_retour "Coefficient du prix" "t" "kg"))
  (setq st_ent (dcl-grid-setcurcell st_ent (groupbib-list (dcl-control-setenabled (st_axeid vl-remove)) in_lon0)))
  (projet_md_metqantprix)
)

(defun c:projet_md_quantite_bt_catedit_onclicked (/ in_lon0 st_ent)
  (entdel 'ls_zons)
  (setq in_lon0 (in_param st_ent gvar_1684_c:projet_md_metqantprix_bt_annuler_onclicked))
  (setq in_lon0 (in_retour "Coefficient du prix" 'ls_entmet in_lon0))
  (setq st_ent (st_rayon st_ent gvar_1684_c:projet_md_metqantprix_bt_annuler_onclicked in_lon0))
  (projet_md_metqantprix)
)

(defun c:projet_md_quantite_bt_catsup_onclicked (/ st_propvalue textpage st_ent)
  (entdel '(bo_go eg_entmet st_unite st_blkname ls_sum))
  T
  (and (setq st_propvalue (re_angle0 gvar_1684_c:projet_md_metqantprix_bt_annuler_onclicked st_ent)) (setq textpage (eo_polyabs st_propvalue)) (open "Coefficient du prix" (geombib-raccordmax 'eg_entmet textpage 'st_unite)) (setq st_ent (blkpolydial-getpoint st_propvalue st_ent)) (projet_md_metqantprix))
)

(defun c:projet_md_quantite_bt_prixnouv_onclicked (/ gvar_2049 vl-remove projet_md_quantite_cb_ltype gvar_1734)
  (entdel "\nQuantité metrée : ")
  (if gvar_1734
    (progn
      (setq gvar_2049 (polybib-lwvertices 'axedyn-reaccreate gvar_1734))
      (setq gvar_2049 (polybib-lwvertices 'ha_handle gvar_2049))
      (setq vl-remove (projet_pa_croisdyn gvar_2049))
    )
    (progn
      (setq vl-remove 0)
    )
  )
  (if gvar_1684_c:projet_md_metqantprix_bt_annuler_onclicked
    (progn
      (setq projet_md_quantite_cb_ltype (*st_sortie* 'metbib-metzgo 'ls_sum "\nCopie dans le presse papier en cours..."))
      (setq gvar_1734 (dcl-grid-setcurcell gvar_1734 (groupbib-list (dcl-control-setenabled (st_axeid vl-remove)) (es_ext gvar_1684_c:projet_md_metqantprix_bt_annuler_onclicked (dcl-grid-addrow 0 projet_md_quantite_cb_ltype) (dcl-grid-addrow 1 projet_md_quantite_cb_ltype) (dcl-grid-addrow 2 projet_md_quantite_cb_ltype) 'en_poly))))
      (c:projet_md_metqantprix_bt_ok_onclicked)
    )
    (progn
      nil
    )
  )
)

(defun c:projet_md_quantite_bt_pp_onclicked (/ local_0 gvar_2049 vl-remove clipboardbib-set gvar_1657 projet_md_quantite_cb_ltype gvar_1734)
  (entdel '*in_dec*)
  (if gvar_1734
    (progn
      (setq gvar_2049 (polybib-lwvertices 'axedyn-reaccreate gvar_1734))
      (setq gvar_2049 (polybib-lwvertices 'ha_handle gvar_2049))
      (setq vl-remove (projet_pa_croisdyn gvar_2049))
    )
    (progn
      (setq vl-remove 0)
    )
  )
  (setq clipboardbib-set (metz-2clipboard))
  (setq gvar_1657 (vl-acad-defun (ha_import clipboardbib-set 'metz-2window)))
  (if gvar_1684_c:projet_md_metqantprix_bt_annuler_onclicked
    (progn
      (setq local_0 gvar_1657)
      (foreach projet_md_quantite_cb_ltype local_0
        (setq vl-remove (st_axeid vl-remove))
        (setq projet_md_quantite_cb_ltype (ha_import projet_md_quantite_cb_ltype '(bo_ok en_hach eo_hach)))
        (setq gvar_1734 (dcl-grid-setcurcell gvar_1734 (groupbib-list (dcl-control-setenabled vl-remove) (es_ext gvar_1684_c:projet_md_metqantprix_bt_annuler_onclicked (dcl-grid-addrow 0 projet_md_quantite_cb_ltype) (dcl-grid-addrow 1 projet_md_quantite_cb_ltype) (dcl-grid-addrow 2 projet_md_quantite_cb_ltype) 'en_poly))))
      )
    )
  )
  (c:projet_md_metqantprix_bt_ok_onclicked)
)

(defun c:projet_md_quantite_bt_prixedit_onclicked (/ vla-get-elevation in_lon0 gvar_1653 gvar_1652 projet_md_quantite_cb_ltype gvar_1734)
  (entdel 'metbib-aire)
  (setq vla-get-elevation (dcl-grid-addrow 1 (in_param gvar_1734 gvar_1679)))
  (setq in_lon0 (dcl-grid-addrow 2 (in_param gvar_1734 gvar_1679)))
  (setq gvar_1653 (dcl-grid-addrow 3 (in_param gvar_1734 gvar_1679)))
  (if (setq gvar_1652 (*st_sortie* vla-get-elevation in_lon0 gvar_1653))
    (progn
      (setq projet_md_quantite_cb_ltype (in_param gvar_1734 gvar_1679))
      (setq projet_md_quantite_cb_ltype (row (dcl-grid-addrow 0 gvar_1652) 1 projet_md_quantite_cb_ltype))
      (setq projet_md_quantite_cb_ltype (row (dcl-grid-addrow 1 gvar_1652) 2 projet_md_quantite_cb_ltype))
      (setq projet_md_quantite_cb_ltype (row (dcl-grid-addrow 2 gvar_1652) 3 projet_md_quantite_cb_ltype))
      (setq gvar_1734 (st_rayon gvar_1734 gvar_1679 projet_md_quantite_cb_ltype))
      (c:projet_md_metqantprix_bt_ok_onclicked)
    )
    (progn
      nil
    )
  )
)

(defun c:projet_md_quantite_bt_prixsup_onclicked (/ projet_md_quantite_cb_ltype ls_zon gvar_1734)
  (entdel 'ls_index)
  T
  (and (setq projet_md_quantite_cb_ltype (re_angle0 gvar_1679 gvar_1734)) (setq ls_zon (va_bande projet_md_quantite_cb_ltype)) (open "Coefficient du prix" (geombib-raccordmax '(inc ls_zonsum st_out) ls_zon 'st_unite)) (setq gvar_1734 (blkpolydial-getpoint projet_md_quantite_cb_ltype gvar_1734)) (c:projet_md_metqantprix_bt_ok_onclicked))
)

(defun c:projet_md_quantite_bt_prixup_onclicked (/ projet_md_quantite_cb_ltype polybib-subpolyoffinv gvar_1734)
  (entdel 'st_out)
  T
  (setq projet_md_quantite_cb_ltype (re_angle0 gvar_1679 gvar_1734))
  (setq polybib-subpolyoffinv (laybib-newlay projet_md_quantite_cb_ltype gvar_1734))
  (ls_som0)
  (and (st_blkbase polybib-subpolyoffinv 0) (setq gvar_1734 (st_out gvar_1734 polybib-subpolyoffinv (vla-get-name polybib-subpolyoffinv))) (c:projet_md_metqantprix_bt_ok_onclicked) (ls_group gvar_1678 (laybib-newlay projet_md_quantite_cb_ltype gvar_1741) 255))
)

(defun c:projet_md_quantite_bt_prixdown_onclicked (/ projet_md_quantite_cb_ltype polybib-subpolyoffinv gvar_1734)
  (entdel 'st_out)
  T
  (setq projet_md_quantite_cb_ltype (re_angle0 gvar_1679 gvar_1734))
  (setq polybib-subpolyoffinv (laybib-newlay projet_md_quantite_cb_ltype gvar_1734))
  (ls_som0)
  (and (repdyn-getpoint (laybib-newlay projet_md_quantite_cb_ltype gvar_1741) (vla-get-name (st_ray2 gvar_1741))) (setq gvar_1734 (st_out gvar_1734 polybib-subpolyoffinv (st_axeid polybib-subpolyoffinv))) (c:projet_md_metqantprix_bt_ok_onclicked) (ls_group gvar_1678 (laybib-newlay projet_md_quantite_cb_ltype gvar_1741) 255))
)

(defun c:projet_md_quantite_bt_prixgo_onclicked (/ projet_md_quantite_cb_ltype ls_zon)
  T
  (and (setq projet_md_quantite_cb_ltype (in_param gvar_1734 gvar_1679)) (setq ls_zon (dcl-grid-addrow 2 projet_md_quantite_cb_ltype)) (open "Coefficient du prix" (geombib-raccordmax " " ls_zon 'st_unite)) (re_abs1 gvar_1645 12))
)

(defun c:projet_md_quantite_bt_qtnouv_onclicked (/ gvar_2049 vl-remove in_lon0 cddr ls_ref gvar_1718)
  (entdel "\nHors zone : ")
  (if gvar_1718
    (progn
      (setq gvar_2049 (polybib-lwvertices 'axedyn-reaccreate gvar_1718))
      (setq gvar_2049 (polybib-lwvertices 'ha_handle gvar_2049))
      (setq vl-remove (projet_pa_croisdyn gvar_2049))
    )
    (progn
      (setq vl-remove 0)
    )
  )
  (setq in_lon0 (geombib-raccordmax 're_rayii (dcl-control-setenabled (st_axeid vl-remove))))
  (if (setq cddr (cddr in_lon0 nil))
    (progn
      (setq ls_ref (polybib-lwvertices 'ls_zonsum (re_x cddr)))
      (setq gvar_1718 (dcl-grid-setcurcell gvar_1718 (groupbib-list (dcl-control-setenabled (st_axeid vl-remove)) (es_ext gvar_1684_c:projet_md_metqantprix_bt_annuler_onclicked ls_ref (axedyn-reaccreate cddr)))))
      (c:projet_md_metqantprix_bt_ok_onclicked)
    )
    (progn
      nil
    )
  )
)

(defun c:projet_md_quantite_bt_qtedit_onclicked (/ ls_entsnew polybib-subpolyoffinv gvar_1639 ls_ref gvar_1637 gvar_1718)
  (entdel "-")
  T
  (and (setq ls_entsnew (blkpoly-ls_entsnew gvar_1678)) (setq polybib-subpolyoffinv (dcl-grid-addrow (re_x ls_entsnew) 4)) (setq gvar_1639 (dcl-grid-addrow polybib-subpolyoffinv gvar_1742)) (setq ls_ref (polybib-lwvertices '*ls_zons* (dcl-grid-addrow 2 gvar_1639))) (setq gvar_1637 (cddr (dcl-grid-addrow 3 gvar_1639) ls_ref)) (setq ls_ref (polybib-lwvertices 'ls_zonsum (re_x gvar_1637))) (setq gvar_1718 (st_rayon gvar_1718 (axedyn-reaccreate gvar_1639) (es_ext gvar_1684_c:projet_md_metqantprix_bt_annuler_onclicked ls_ref (axedyn-reaccreate gvar_1637)))) (c:projet_md_metqantprix_bt_ok_onclicked))
)

(defun c:projet_md_quantite_bt_qtsup_onclicked (/ ls_entsnew polybib-subpolyoffinv gvar_1639 gvar_1635 gvar_1718)
  (entdel 'in_dec)
  (setq ls_entsnew (blkpoly-ls_entsnew gvar_1678))
  (setq polybib-subpolyoffinv (dcl-grid-addrow (re_x ls_entsnew) 4))
  T
  (and (st_blkbase polybib-subpolyoffinv 0) (setq gvar_1639 (dcl-grid-addrow polybib-subpolyoffinv gvar_1718)) (setq gvar_1635 (dcl-grid-addrow 3 gvar_1639)) (open "Coefficient du prix" (geombib-raccordmax 'st_clip gvar_1635 'st_unite)) (setq gvar_1718 (blkpolydial-getpoint gvar_1639 gvar_1718)) (c:projet_md_metqantprix_bt_ok_onclicked))
)

(defun c:projet_md_quantite_bt_qtgauche_onclicked (/ ls_entsnew polybib-subpolyoffinv gvar_1718)
  (entdel ",")
  T
  (setq ls_entsnew (blkpoly-ls_entsnew gvar_1678))
  (setq polybib-subpolyoffinv (dcl-grid-addrow (re_x ls_entsnew) 4))
  (ls_som0)
  (and (st_blkbase polybib-subpolyoffinv 0) (setq gvar_1718 (st_out gvar_1718 polybib-subpolyoffinv (vla-get-name polybib-subpolyoffinv))) (c:projet_md_metqantprix_bt_ok_onclicked) (ls_group gvar_1678 (axedyn-reaccreate ls_entsnew) (dcl-grid-addrow (re_x ls_entsnew) 1)))
)

(defun c:projet_md_quantite_bt_qtdroite_onclicked (/ ls_entsnew polybib-subpolyoffinv gvar_1718)
  (entdel ".")
  T
  (setq ls_entsnew (blkpoly-ls_entsnew gvar_1678))
  (setq polybib-subpolyoffinv (dcl-grid-addrow (re_x ls_entsnew) 4))
  (ls_som0)
  (and (repdyn-getpoint polybib-subpolyoffinv (vla-get-name (st_ray2 gvar_1718))) (setq gvar_1718 (st_out gvar_1718 polybib-subpolyoffinv (st_axeid polybib-subpolyoffinv))) (c:projet_md_metqantprix_bt_ok_onclicked) (ls_group gvar_1678 (axedyn-reaccreate ls_entsnew) (st_syle (re_x ls_entsnew) 1)))
)

(defun c:projet_md_quantite_zl_cat_onselchanged (/ eo_poly arg_2)
  (entdel 'vl-string-subst)
  (if eo_poly_2
    (progn
      (c:projet_md_metqantprix_bt_ok_onclicked)
      (vl-string-subst 254 254)
    )
    (progn
      nil
    )
  )
)

(defun metquant-dial-gr_prixfill (/ local_0 local_1 gvar_1742 gvar_1741 polybib-subpolyoffinv gvar_1684_c:projet_md_metqantprix_bt_annuler_onclicked projet_md_quantite_cb_ltype gvar_1639 gvar_3169 gvar_1679 st_type0 en_entmet gvar_1624 gvar_1623)
  (entdel "=LC4*LC(-1)")
  (*en_ins* gvar_1678)
  (setq gvar_1742 (es_ext))
  (setq gvar_1741 (es_ext))
  (while (st_blkbase (eo_plf gvar_1678) 4)
    (eo_plf gvar_1678 4)
  )
  (setq local_0 gvar_1734)
  (and (setq polybib-subpolyoffinv (eg_entmet0 gvar_1682_c:projet_md_metqantprix_cb_unit_onselchanged)) (st_blkbase polybib-subpolyoffinv 255) (setq gvar_1684_c:projet_md_metqantprix_bt_annuler_onclicked (axedyn-reaccreate (dcl-grid-addrow polybib-subpolyoffinv st_ent))))
  (foreach projet_md_quantite_cb_ltype local_0
    (if (ls_ext2 gvar_1684_c:projet_md_metqantprix_bt_annuler_onclicked (dcl-grid-addrow 1 projet_md_quantite_cb_ltype))
      (progn
        (eo_blkpop gvar_1678 (dcl-grid-addrow 2 projet_md_quantite_cb_ltype) (dcl-grid-addrow 3 projet_md_quantite_cb_ltype) (dcl-grid-addrow 4 projet_md_quantite_cb_ltype) (eo_blkbase (dcl-grid-addrow 5 projet_md_quantite_cb_ltype) 2 3))
        (setq gvar_1741 (dcl-grid-setcurcell gvar_1741 projet_md_quantite_cb_ltype))
      )
    )
  )
  (setq local_0 gvar_1718)
  (foreach gvar_1639 local_0
    (if (ls_ext2 gvar_1684_c:projet_md_metqantprix_bt_annuler_onclicked (dcl-grid-addrow 1 gvar_1639))
      (progn
        (eg_entmet0 gvar_1678 (eo_plf gvar_1678) (es_ext (dcl-grid-addrow 3 gvar_1639) 1 45))
        (setq gvar_1742 (dcl-grid-setcurcell gvar_1742 gvar_1639))
      )
    )
  )
  (setq gvar_3169 0)
  (setq local_0 gvar_1741)
  nil
  (foreach projet_md_quantite_cb_ltype local_0
    (setq gvar_1679 (axedyn-reaccreate projet_md_quantite_cb_ltype))
    (setq st_type0 4)
    (setq local_1 gvar_1742)
    (foreach gvar_1639 local_1
      (setq en_entmet (axedyn-reaccreate gvar_1639))
      (if (setq gvar_1624 (eo_polyabs (re_angle0 (geombib-raccordmax gvar_1679 'vla-get-backgroundcolor en_entmet) f)))
        (progn
          (en_blk gvar_1678 gvar_3169 st_type0 gvar_1623)
          (setq gvar_1623 (eo_blkbase gvar_1624 2 3))
        )
      )
      (setq st_type0 (st_axeid st_type0))
    )
    (setq gvar_3169 (st_axeid gvar_3169))
  )
  T
  T
)

(defun c:projet_md_quantite_gr_prix_onselchanged (/ eq netbib-purgeblock projet_md_quantite_cb_ltype gvar_1621 gvar_1639 en_entmet ls_handle ls_ref)
  (entdel 'vla-put-elevation)
  (if (re_deltax eq_2 0)
    (progn
      (setq projet_md_quantite_cb_ltype (dcl-grid-addrow eq_2 gvar_1741))
      (setq gvar_1621 polybib-vtxjoin)
    )
  )
  (if (st_blkbase netbib-purgeblock_2 3)
    (progn
      (in_retour ls_ref (dcl-grid-addrow 4 gvar_1639))
      (setq gvar_1639 (dcl-grid-addrow (dcl-grid-addrow netbib-purgeblock_2 4) gvar_1742))
      (setq en_entmet (axedyn-reaccreate gvar_1639))
      (setq ls_handle polybib-vtxjoin)
      (setq gvar_1621 nil)
      (setq ls_ref (dcl-grid-addrow 2 gvar_1639))
    )
    (progn
      (in_retour nil nil)
      (setq gvar_1621 polybib-vtxjoin)
      (setq gvar_1639 nil)
      (setq en_entmet nil)
      (setq ls_handle nil)
      (setq ls_ref nil)
    )
  )
  (if (re_angle netbib-purgeblock_2 254)
    (progn
      (setq gvar_1621 nil)
    )
  )
  (vlax-vla-object->ename gvar_1619 gvar_1621)
  (vlax-vla-object->ename bo_visi gvar_1621)
  (vlax-vla-object->ename bo_hili gvar_1621)
  (vlax-vla-object->ename gvar_1616 gvar_1621)
  (vlax-vla-object->ename ls_szon gvar_1621)
  (vlax-vla-object->ename en_szon ls_handle)
  (vlax-vla-object->ename vla-highlight ls_handle)
  (vlax-vla-object->ename gvar_1612 ls_handle)
  (vlax-vla-object->ename gvar_1611 ls_handle)
)

(defun c:projet_md_quantite_gr_prix_oncolumnclick (/ netbib-purgeblock)
  (ls_ptinint 'ls_zonhand 'close)
)

(defun c:projet_md_quantite_gr_prix_ondblclicked (/ eq netbib-purgeblock projet_md_quantite_cb_ltype gvar_1679 gvar_1639 en_entmet pt_2d gvar_1623 gvar_1624 f gvar_1741 gvar_1734)
  (entdel '(en_poly2 pt_2 pt_2d pt_2f ls_exts ls_ext ls_offset))
  (setq projet_md_quantite_cb_ltype (dcl-grid-addrow eq_2 gvar_1741))
  (setq gvar_1679 (axedyn-reaccreate projet_md_quantite_cb_ltype))
  nil
  (or (re_angle netbib-purgeblock_2 3) (re_deltax netbib-purgeblock_2 4))
  (vlax-curve-getendparam pt_2d)
  (setq gvar_1639 (dcl-grid-addrow (dcl-grid-addrow netbib-purgeblock_2 4) gvar_1742))
  (setq en_entmet (axedyn-reaccreate gvar_1639))
  (setq pt_2d (geombib-raccordmax gvar_1679 'vla-get-backgroundcolor en_entmet))
  (if (re_angle0 pt_2d f)
    (progn
      (setq gvar_1623 (eo_blkbase (in_param f pt_2d) 2 3))
    )
    (progn
      (setq gvar_1623 'pt_2f)
    )
  )
  (setq gvar_1623 (in_retour "Coefficient du prix" pt_2d gvar_1623))
  (if (cadr (ls_ext2 gvar_1623 'ls_ext1))
    (progn
      (setq gvar_1624 (groupbib-listobj gvar_1623))
      (if (re_angle gvar_1624 'ha_poly)
        (progn
          (setq f (blkpolydial-getpoint (re_angle0 pt_2d f) f))
          (setq gvar_1623 'ls_ext1)
        )
        (progn
          (setq f (st_rayon f pt_2d gvar_1624))
          (setq gvar_1623 (eo_blkbase gvar_1624 2 3))
        )
      )
      (en_blk gvar_1678 eq_2 netbib-purgeblock_2 gvar_1623)
    )
    (progn
      nil
    )
  )
  (setq gvar_1623 (eo_blkbase (dcl-grid-addrow 5 projet_md_quantite_cb_ltype) 2 3))
  (setq gvar_1623 (in_retour "Coefficient du prix" "pt_1d" gvar_1623))
  (setq gvar_1624 (groupbib-listobj gvar_1623))
  (if (projet_pa_axes_st_desc gvar_1624 'ha_poly)
    (progn
      (setq projet_md_quantite_cb_ltype (row gvar_1624 5 projet_md_quantite_cb_ltype))
      (setq gvar_1741 (st_rayon gvar_1741 gvar_1679 (eo_polyabs projet_md_quantite_cb_ltype)))
      (setq gvar_1734 (st_rayon gvar_1734 gvar_1679 (eo_polyabs projet_md_quantite_cb_ltype)))
      (setq gvar_1623 (eo_blkbase gvar_1624 2 3))
      (en_blk gvar_1678 eq_2 netbib-purgeblock_2 gvar_1623)
    )
    (progn
      nil
    )
  )
)

(defun c:projet_md_quantite_bt_sauv_onclicked (/ blkbib-blkeffname gvar_1577)
  (entdel 'pt_1d)
  (mpolydyn-ext (ls_exts nil st_ent) gvar_1577)
  (mpolydyn-ext (ls_exts nil gvar_1734) gvar_1577)
  (mpolydyn-ext (ls_exts nil gvar_1718) gvar_1577)
  (mpolydyn-ext (ls_exts nil f) gvar_1577)
  (setq blkbib-blkeffname (projet_pa_bordyn_st_style 'polybib-distproj (trans "OC-Bordyn") "pt_1f" 1))
  (setq gvar_1577 (pt_1f blkbib-blkeffname 'pt_1f))
  (ef_ref1 gvar_1577)
)

(defun metqquant-load (/ local_0 local_1 blkbib-blkeffname gvar_1577 st_propvalue projet_md_quantite_cb_ltype gvar_1639 open gvar_1719 gvar_1563 gvar_2149 ld_mpolydyn ls_ref)
  (entdel 'va_abs1)
  (if (setq blkbib-blkeffname (projet_pa_bordyn_st_style 'polybib-distproj (trans "OC-Bordyn") "pt_1f" 0))
    (progn
      (ls_som0 'va_abs1f)
      (ls_som0 'va_abs1d)
      (ls_som0 '(va_abs2 va_abs en_poly re_abs1))
      (ls_som0 'va_abs2)
      (ef_ref1 gvar_1577)
      (setq gvar_1577 (pt_1f blkbib-blkeffname '(re_abs0 en_poly1 en_poly2 va_abs1d va_abs1f va_abs2d)))
      (setq st_propvalue (re_abs1f (va_abs2d gvar_1577)))
      (setq projet_md_quantite_cb_ltype (re_abs1f (va_abs2d gvar_1577)))
      (setq gvar_1639 (re_abs1f (va_abs2d gvar_1577)))
      (setq open (re_abs1f (va_abs2d gvar_1577)))
      (setq st_propvalue st_propvalue)
      (setq st_propvalue (polybib-lwvertices 'st_stylepoly st_propvalue))
      (setq projet_md_quantite_cb_ltype (polybib-lwvertices '(in_id st_id ld_mpolydyn ha_poly va_ent) projet_md_quantite_cb_ltype))
      (setq gvar_1719 (es_ext))
      (setq gvar_1563 gvar_1639)
      (setq local_0 gvar_1563)
      (foreach gvar_1639 local_0
        (setq gvar_1639 (axedyn-reaccreate gvar_1639))
        (setq gvar_2149 (dcl-grid-addrow 2 gvar_1639))
        (setq ld_mpolydyn (es_ext))
        (setq local_1 (axedyn-reaccreate gvar_2149))
        (foreach ls_ref local_1
          (setq ls_ref (ld_mpolydyn ls_ref))
          (setq ld_mpolydyn (dcl-grid-setcurcell ld_mpolydyn (groupbib-list (axedyn-reaccreate ls_ref) (re_x ls_ref))))
        )
        (setq gvar_1719 (dcl-grid-setcurcell gvar_1719 (es_ext (axedyn-reaccreate (dcl-grid-addrow 0 gvar_1639)) (axedyn-reaccreate (dcl-grid-addrow 1 gvar_1639)) ld_mpolydyn (axedyn-reaccreate (dcl-grid-addrow 3 gvar_1639)))))
      )
      (setq open (polybib-lwvertices "Impossible d'ajouter les parents" open))
    )
    (progn
      nil
    )
  )
)

(defun c:projet_md_quantite_bt_load_onclicked (/ st_ent f)
  (entdel 'mpolydyn-getparents)
  (if (and (st_coefid) (open "Coefficient du prix" '(st_path f)))
    (progn
      (setq st_ent st_propvalue)
      (setq f open)
      (if (dcl-grid-clear gvar_1645)
        (progn
          (projet_md_metqantprix)
          (c:projet_md_metqantprix_bt_ok_onclicked)
        )
      )
      (if (dcl-grid-clear jsonbib-list2json)
        (progn
          (st_value gvar_1745 (polybib-lwvertices 'eo_polyabs st_ent))
        )
      )
    )
  )
  (ls_som0)
)

(defun c:projet_md_quantite_boutonimage1_onclicked ()
  (re_abs1 gvar_1645 2)
)

(defun metz-2window (re_absfin mpolydyndial-changeamontaval / local_2 st_ray2 gvar_1509 gvar_1502 gvar_1635)
  (entdel 'projet_pa_mpolydyn_gr_elements)
  (setq st_ray2 0)
  (setq gvar_1509 'ls_ext1)
  (setq gvar_1509 (geombib-raccordmax gvar_1509 "Choix du segment à ajouter : " (eo_blkbase (eo_polyabs (axedyn-reaccreate re_absfin)) 2 2) '(ls_deb ls_ent ls_fin) mpolydyndial-changeamontaval))
  (if (st_blkbase (st_ray2 re_absfin) 2)
    (progn
      (setq gvar_1509 (geombib-raccordmax gvar_1509 '(ls_deb ls_ent ls_fin inc ha_ent st_deb st_fin) (eo_blkbase (dcl-grid-addrow (eo_polyabs (axedyn-reaccreate re_absfin)) (eo_polyabs (re_x re_absfin))) 2 2) '(ls_deb ls_ent ls_fin) mpolydyndial-changeamontaval))
      (setq gvar_1509 (geombib-raccordmax gvar_1509 'st_deb (eo_blkbase (eo_polyabs (re_x re_absfin)) 2 2) '(ls_deb ls_ent ls_fin) mpolydyndial-changeamontaval))
      (setq gvar_1509 (geombib-raccordmax gvar_1509 'st_fin))
      (setq local_2 (aobib-getnom re_absfin))
      (foreach gvar_1502 local_2
        (if (odclbib-fillcombo (eo_polyabs gvar_1502) 'ha_poly)
          (progn
            (setq gvar_1635 '(st_rac ls_fin va_fin))
          )
          (progn
            (setq gvar_1635 (eo_blkbase (eo_polyabs gvar_1502) 2 2))
          )
        )
        (setq gvar_1509 (geombib-raccordmax gvar_1509 'va_amav (re_x (dcl-grid-addrow st_ray2 cb_amav)) 'bt_amav gvar_1635 '(ls_deb ls_ent ls_fin) mpolydyndial-changeamontaval))
        (setq st_ray2 (st_axeid st_ray2))
      )
    )
  )
  gvar_1509
)

(defun metz-2clipboard (/ re_absfin polybib-subpolybisinv st_amav local_3 local_4 gvar_1502 gvar_1635)
  (entdel 'mpolydyndial-selectamontaval)
  (setq st_amav 'ls_ext1)
  (if (cadr st_amav)
    (progn
      (setq st_amav 0)
    )
  )
  (setq local_3 (vl-acad-defun (aobib-getnom re_absfin)))
  (foreach gvar_1502 local_3
    (if (odclbib-fillcombo (eo_polyabs gvar_1502) 'ha_poly)
      (progn
        (setq gvar_1635 'ls_ext1)
      )
      (progn
        (setq gvar_1635 (va_rac 'ls_amav 'va_rac (eo_blkbase (eo_polyabs gvar_1502) 2 2)))
      )
    )
    (or (or (re_angle polybib-subpolybisinv 'metbib-metzgo) (re_angle polybib-subpolybisinv '(in_amont in_aval ls_deb ls_ent ls_fin st_amont st_aval))) polybib-vtxjoin)
    (setq st_amav (geombib-raccordmax st_amav gvar_1635 '(bo_ok en_hach eo_hach)))
    (setq local_4 st_amav)
    (while (<= local_4 0)
      (setq local_4 (1- local_4))
      (setq st_amav (geombib-raccordmax st_amav '(bo_ok en_hach eo_hach)))
    )
    (setq st_amav (geombib-raccordmax st_amav gvar_1635 'repdyn-getpointangle))
    (setq local_4 st_amav)
    (while (<= local_4 0)
      (setq local_4 (1- local_4))
      (setq st_amav (geombib-raccordmax st_amav 'repdyn-getpointangle))
    )
    (setq st_amav (geombib-raccordmax st_amav gvar_1635 '(bo_ok en_hach eo_hach) 'in_amont '(bo_ok en_hach eo_hach)))
    (setq local_4 st_amav)
    (while (<= local_4 0)
      (setq local_4 (1- local_4))
      (setq st_amav (geombib-raccordmax st_amav '(bo_ok en_hach eo_hach)))
    )
  )
  (setq gvar_1502 (fas-1- re_absfin))
  (if (odclbib-fillcombo (eo_polyabs gvar_1502) 'ha_poly)
    (progn
      (setq gvar_1635 'ls_ext1)
    )
    (progn
      (setq gvar_1635 (va_rac 'ls_amav 'va_rac (eo_blkbase (eo_polyabs gvar_1502) 2 2)))
    )
  )
  (or (or (re_angle polybib-subpolybisinv 'metbib-metzgo) (re_angle polybib-subpolybisinv '(in_amont in_aval ls_deb ls_ent ls_fin st_amont st_aval))) polybib-vtxjoin)
  (setq st_amav (geombib-raccordmax st_amav gvar_1635))
  (setq st_amav (geombib-raccordmax st_amav gvar_1635))
  (setq st_amav (geombib-raccordmax st_amav gvar_1635 '(bo_ok en_hach eo_hach) 'in_amont))
  st_amav
)

(defun mpolydyn-list ()
  (axedyn-setrayext '(lambda (ls_importconf) (= st_sourceid (listbib-key (cdr ls_importconf) "st_SourceId"))))
)

(defun mpolydyn-get (inters / local_1 projet_md_picklayer va_echelle)
  (entdel 'c:projet_md_picklayer_gr_layers_onselchanged)
  (setq projet_md_picklayer (es_ext))
  (setq va_echelle (re_courant '(lambda (ls_importconf) (= st_sourceid (listbib-key (cdr ls_importconf) "st_SourceId"))) inters))
  (if (cadr (in_param va_echelle 'c:projet_md_picklayer_bt_ok_onclicked))
    (progn
      (setq local_1 (st_ray2 (in_param va_echelle 'stylepoly-fillcombo)))
      (while (<= local_1 0)
        (setq local_1 (1- local_1))
        (setq projet_md_picklayer (dcl-grid-setcurcell projet_md_picklayer 0))
      )
      (setq va_echelle (dcl-grid-setcurcell va_echelle (groupbib-list 'c:projet_md_picklayer_bt_ok_onclicked projet_md_picklayer)))
    )
  )
  (st_rayon (es_ext (groupbib-list 'st_type '(lambda (ls_importconf) (= st_sourceid (listbib-key (cdr ls_importconf) "st_SourceId"))))) va_echelle)
)

(defun mpolydyn-set (inters arg_2)
  (entdel 'c:projet_md_picklayer_gr_layers_ondblclicked)
  (fas-rtos3 '(lambda (ls_importconf) (= st_sourceid (listbib-key (cdr ls_importconf) "st_SourceId"))) inters (blkpolydial-getpoint (re_angle0 'st_type arg_2) arg_2))
)

(defun mpolydyn-getparents (arg_1 / local_1 gvar_3094 ls_importsources aopora-fin poly-vlatrace st_sourceid)
  (entdel 'in_somnew)
  (setq gvar_3094 (es_ext))
  (setq ls_importsources (in_param arg_1 "\nBoucle sur les sources"))
  (setq aopora-fin (in_param arg_1 'stylepoly-fillcombo))
  (setq poly-vlatrace (in_param arg_1 'ls_importsource))
  (setq local_1 aopora-fin)
  (foreach st_sourceid local_1
    (setq gvar_3094 (dcl-grid-setcurcell gvar_3094 st_sourceid))
  )
  (setq local_1 (st_rayon ls_importsources poly-vlatrace))
  (foreach st_sourceid local_1
    (if (re_abs2 st_sourceid)
      (progn
        (setq gvar_3094 (dcl-grid-setcurcell gvar_3094 (groupbib-list 're_abs2 st_sourceid)))
      )
    )
  )
  gvar_3094
)

(defun mpolydyn-popgo (inters / gvar_1423 aopora-fin ls_importsources poly-vlatrace projet_md_picklayer gvar_1416 dcl-form-close gvar_2519 polybib_geom-bulge2radius gvar_3265 ls_propsdescs)
  (entdel "re_absMod")
  (if (and gvar_3345 (dcl-grid-clear gvar_1417))
    (progn
      (setq gvar_1423 gvar_3345)
    )
    (progn
      (setq gvar_1423 (projet_md_metprop_bt_layer inters))
    )
  )
  (if (and (and gvar_1423 (setq aopora-fin (in_param gvar_1423 'stylepoly-fillcombo)) (setq ls_importsources (in_param gvar_1423 "\nBoucle sur les sources")) (setq poly-vlatrace (in_param gvar_1423 'ls_importsource)) (setq projet_md_picklayer (in_param gvar_1423 'c:projet_md_picklayer_bt_ok_onclicked)) (setq gvar_1416 (in_param gvar_1423 'ls_somnew)) (setq dcl-form-close (polydyn-makesom)) (setq gvar_2519 (polydyn-makesom (in_param gvar_1423 'dcl-form-show))) (setq polybib_geom-bulge2radius (pt_proj (in_param gvar_1423 'dcl-form-show))) (setq polybib_geom-bulge2radius (dcl-grid-setcurcell polybib_geom-bulge2radius (groupbib-list 70 (st_syle 128 gvar_1416))))) (and (re_angle gvar_1416 1) (ls_ext2 'ha_poly (pt_ref (in_param (axedyn-reaccreate dcl-form-close) 10) (in_param (fas-1- dcl-form-close) 10)) 'polydyn-makelists)))
    (progn
      (setq dcl-form-close (vl-acad-defun dcl-form-close))
    )
  )
  (if (and (setq gvar_3265 (in_param gvar_1423 'ls_importfilters)) (setq ls_propsdescs (en_refoffset gvar_3265)))
    (progn
      (sssetfirst ls_propsdescs dcl-form-close polybib_geom-bulge2radius)
    )
    (progn
      (setq ls_propsdescs (*en_ray* dcl-form-close polybib_geom-bulge2radius))
      (setq gvar_3265 (fas-1- ls_propsdescs))
      (setq gvar_1423 (st_rayon gvar_1423 'ls_importfilters gvar_3265))
      (st_sourceid inters gvar_1423)
    )
  )
  T
  gvar_3265
  T
)

(defun c:projet_pa_mpolydyn_oninitialize (/ projet_pa_polydyn aopora-fin)
  (in_param gvar_3345 'dcl-form-show)
  (ls_vtx0 gvar_1409 (polybib-lwvertices 'eo_polyabs projet_pa_polydyn))
  (ls_vtx0 gvar_1408 (polybib-lwvertices 'eo_polyabs projet_pa_polydyn))
  (ls_vtx0 en_rep (polybib-lwvertices 'ha_polyext (ls_dist)))
  (setq projet_pa_polydyn (es_ext (groupbib-list "Reconstruction des réacteurs des paramètres" 'eo_blkparam) (groupbib-list 'ls_paramentxy 'blkbib-blk_temp) (groupbib-list 're_rayii '(inc ls_filters ls_filter)) (groupbib-list '(lambda (ls_elem) (= "H" (listbib-key ls_elem "st_type"))) 'polydyn-tracerep) (groupbib-list '(re_x re_y pt_poly re_anglepoly re_angle) 'eg_blkbase) (groupbib-list 'blkpoly-poly "ha_parent")))
  (setq aopora-fin (in_param gvar_3345 'stylepoly-fillcombo))
  (if (laybib-newlay (in_param gvar_3345 'dcl-form-show) (polybib-lwvertices 'axedyn-reaccreate (ls_dist)))
    (progn
      (bo_invpoly1 en_rep (laybib-newlay (in_param gvar_3345 'dcl-form-show) (polybib-lwvertices 'axedyn-reaccreate (ls_dist))))
    )
  )
  (bo_lctabs gvar_1406 (en_polyabs gvar_3345 'ls_obj 'st_abs))
  (ls_vtx0 re_absmod (es_ext 'st_offset 'va_offset))
  (bo_invpoly1 re_absmod (in_param gvar_3345 'ls_somnew))
  (st_num re_offsetmod 0)
  (va_pente)
  (ls_som0)
)

(defun c:projet_pa_mpolydyn_gr_elements_onselchanged (/ eq netbib-purgeblock polybib-perpoint ls_importsources aopora-fin poly-vlatrace projet_md_picklayer polydyn-edit-fillgrid pt_pas ls_inters1 pt_absdyn gvar_1392 polydyncc gvar_1386 dcl-form-close gvar_1397)
  (entdel "va_pente")
  (sihpp-list gvar_1397)
  (polybib-perpoint polydyn-edit-fillgrid nil)
  (setq polybib-perpoint eq_2)
  (if (re_deltax polybib-perpoint 0)
    (progn
      (bo_invpoly1 gvar_1409 (aopora-deb pt_pas))
      (bo_invpoly1 gvar_1408 (aopora-deb ls_inters1))
      (st_num re_offsetmod pt_absdyn)
      (re_1 gvar_1392 pt_pas gvar_1409 re_1)
      (re_1 gvar_1392 ls_inters1 gvar_1408 re_2)
      (polybib-perpoint polydyn-edit-fillgrid 1)
      (setq ls_importsources (in_param gvar_3345 "\nBoucle sur les sources"))
      (setq aopora-fin (in_param gvar_3345 'stylepoly-fillcombo))
      (setq poly-vlatrace (in_param gvar_3345 'ls_importsource))
      (setq projet_md_picklayer (in_param gvar_3345 'c:projet_md_picklayer_bt_ok_onclicked))
      (setq polydyn-edit-fillgrid (re_ray (hachbib-vtxs2hach (dcl-grid-addrow polybib-perpoint aopora-fin))))
      (setq pt_pas (dcl-grid-addrow polybib-perpoint ls_importsources))
      (setq ls_inters1 (dcl-grid-addrow polybib-perpoint poly-vlatrace))
      (setq pt_absdyn (dcl-grid-addrow polybib-perpoint projet_md_picklayer))
      (setq gvar_1392 (dcl-grid-addrow (aopora-deb pt_pas) (polybib-lwvertices 'axedyn-reaccreate projet_pa_polydyn)))
      (setq gvar_1392 (dcl-grid-addrow (aopora-deb ls_inters1) (polybib-lwvertices 'axedyn-reaccreate projet_pa_polydyn)))
      (if (fas-polar1 polydyn-edit-fillgrid)
        (progn
          (setq polydyncc (ls_vtxs2 polybib-perpoint (dcl-grid-addrow polybib-perpoint ls_importsources) "Reconstruction des réacteurs des paramètres"))
          (setq gvar_1386 (ls_vtxs2 polybib-perpoint (dcl-grid-addrow polybib-perpoint poly-vlatrace) 'ls_paramentxy))
          (setq pt_absdyn (odclbib-fillcombo 1 (dcl-grid-addrow polybib-perpoint projet_md_picklayer)))
          (if (projet_pa_axes_st_desc polydyncc gvar_1386)
            (progn
              (ls_options (dcl-forcedwgredraw gvar_1397) 80)
              (ls_options (dcl-forcedwgredraw gvar_1397) 're_long)
              (ls_options (dcl-forcedwgredraw gvar_1397) 4)
              (boxlib-optionbox gvar_1397 4)
              (setq dcl-form-close (polycc-side polydyn-edit-fillgrid polydyncc gvar_1386 pt_absdyn))
              (setq gvar_1397 (gr_filterupdate dcl-form-close nil))
            )
          )
        )
        (progn
          (bordyn-inters 'pt_c1)
        )
      )
    )
  )
  (bo_visible)
  (ls_som0)
)

(defun c:projet_pa_mpolydyn_gr_elements_ondblclicked (/ eq netbib-purgeblock)
  (pt_c2 gvar_1397 polybib-vtxjoin)
)

(defun c:projet_pa_mpolydyn_bt_insert_onclicked (/ pt_tan ls_propsdescs pt_inters gvar_2767 re_2max ls_importsources aopora-fin poly-vlatrace projet_md_picklayer polycc-tanint polycc-tanext chemdyn-hachtrace gvar_2532 re_bu1 re_bu2 gvar_3345)
  (entdel 're_1max)
  (setq ls_importsources (in_param gvar_3345 "\nBoucle sur les sources"))
  (setq aopora-fin (in_param gvar_3345 'stylepoly-fillcombo))
  (setq poly-vlatrace (in_param gvar_3345 'ls_importsource))
  nil
  (and (and (and (and (and polybib-perpoint (st_blkbase polybib-perpoint 255) (setq pt_tan (pt_proj2 'pt_proj1 nil (groupbib-list '(lambda (ls_importconf) (= st_sourceid (listbib-key (cdr ls_importconf) "st_SourceId"))) re_yinv))) (setq ls_propsdescs (re_ray (hachbib-vtxs2hach (axedyn-reaccreate pt_tan)))) (setq pt_inters (re_ray (in_param gvar_3345 'ls_importfilters))) (setq gvar_2767 (re_x pt_tan)) (setq re_2max (blkpoly-lsparams polybib-perpoint 0)) (setq projet_md_picklayer (in_param gvar_3345 'c:projet_md_picklayer_bt_ok_onclicked)) (setq polycc-tanint (projet_ml_progress ls_propsdescs)) (setq polycc-tanext (projet_md_metprop ls_propsdescs)) (setq chemdyn-hachtrace (palbib-init pt_inters polycc-tanint)) (setq gvar_2532 (palbib-init pt_inters polycc-tanext)) (setq re_bu1 (polybib_geom-arc->bulge re_yinv chemdyn-hachtrace)) (setq re_bu2 (polybib_geom-arc->bulge re_yinv gvar_2532))) (and (ls_ext2 polybib-perpoint re_bu2) (ls_ext2 polybib-perpoint re_bu1) (repdyn-getpoint chemdyn-hachtrace gvar_2532))) (and (ls_ext2 polybib-perpoint re_bu2) (ls_ext2 polybib-perpoint re_bu1) (st_blkbase chemdyn-hachtrace gvar_2532))) (repdyn-getpoint chemdyn-hachtrace gvar_2532)) (st_blkbase chemdyn-hachtrace gvar_2532))
  (setq aopora-fin (blkpoly-insdetail (axedyn-reaccreate pt_tan) re_2max aopora-fin))
  (setq ls_importsources (blkpoly-insdetail 'ls_paramentxy re_2max ls_importsources))
  (setq poly-vlatrace (blkpoly-insdetail "Reconstruction des réacteurs des paramètres" re_2max poly-vlatrace))
  (setq projet_md_picklayer (blkpoly-insdetail 0 re_2max projet_md_picklayer))
  (setq aopora-fin (blkpoly-insdetail (axedyn-reaccreate pt_tan) re_2max aopora-fin))
  (setq ls_importsources (blkpoly-insdetail "Reconstruction des réacteurs des paramètres" re_2max ls_importsources))
  (setq poly-vlatrace (blkpoly-insdetail 'ls_paramentxy re_2max poly-vlatrace))
  (setq projet_md_picklayer (blkpoly-insdetail 0 re_2max projet_md_picklayer))
  (setq aopora-fin (blkpoly-insdetail (dcl-grid-addrow polybib-perpoint aopora-fin) re_2max aopora-fin))
  (setq aopora-fin (blkpoly-insdetail (axedyn-reaccreate pt_tan) (st_axeid re_2max) aopora-fin))
  (setq ls_importsources (blkpoly-insdetail 'ls_paramentxy re_2max ls_importsources))
  (setq ls_importsources (blkpoly-insdetail 're_rayii re_2max ls_importsources))
  (setq poly-vlatrace (blkpoly-insdetail "Reconstruction des réacteurs des paramètres" re_2max poly-vlatrace))
  (setq poly-vlatrace (blkpoly-insdetail 're_rayii re_2max poly-vlatrace))
  (setq projet_md_picklayer (blkpoly-insdetail 0 re_2max projet_md_picklayer))
  (setq projet_md_picklayer (blkpoly-insdetail 0 re_2max projet_md_picklayer))
  T
  (setq aopora-fin (blkpoly-insdetail (dcl-grid-addrow polybib-perpoint aopora-fin) re_2max aopora-fin))
  (setq aopora-fin (blkpoly-insdetail (axedyn-reaccreate pt_tan) (st_axeid re_2max) aopora-fin))
  (setq ls_importsources (blkpoly-insdetail "Reconstruction des réacteurs des paramètres" re_2max ls_importsources))
  (setq ls_importsources (blkpoly-insdetail 're_rayii re_2max ls_importsources))
  (setq poly-vlatrace (blkpoly-insdetail 'ls_paramentxy re_2max poly-vlatrace))
  (setq poly-vlatrace (blkpoly-insdetail 're_rayii re_2max poly-vlatrace))
  (setq projet_md_picklayer (blkpoly-insdetail 0 re_2max projet_md_picklayer))
  (ls_som0)
  (and (setq projet_md_picklayer (blkpoly-insdetail 0 re_2max projet_md_picklayer)) (setq gvar_3345 (st_rayon gvar_3345 "\nBoucle sur les sources" ls_importsources)) (setq gvar_3345 (st_rayon gvar_3345 'stylepoly-fillcombo aopora-fin)) (setq gvar_3345 (st_rayon gvar_3345 'ls_importsource poly-vlatrace)) (setq gvar_3345 (st_rayon gvar_3345 'c:projet_md_picklayer_bt_ok_onclicked projet_md_picklayer)) (vlax-curve-getendparam gvar_3345) (va_pente) (en_hatch geombib-getinsideangle) (ls_group geombib-getinsideangle (st_axeid re_2max) 0) (st_linkpath re_yinv))
)

(defun c:projet_pa_mpolydyn_bt_add_onclicked (/ pt_tan ls_propsdescs gvar_2767 ls_importsources aopora-fin poly-vlatrace projet_md_picklayer gvar_3345)
  (entdel 'pt_cible)
  T
  (setq ls_importsources (in_param gvar_3345 "\nBoucle sur les sources"))
  (setq aopora-fin (in_param gvar_3345 'stylepoly-fillcombo))
  (setq poly-vlatrace (in_param gvar_3345 'ls_importsource))
  (ls_som0)
  (and (dcl-grid-clear gvar_1417) (setq pt_tan (pt_proj2 '(pt_1 pt_2) nil (groupbib-list '(lambda (ls_importconf) (= st_sourceid (listbib-key (cdr ls_importconf) "st_SourceId"))) re_yinv))) (setq ls_propsdescs (re_ray (hachbib-vtxs2hach (axedyn-reaccreate pt_tan)))) (setq gvar_2767 (re_x pt_tan)) (setq projet_md_picklayer (in_param gvar_3345 'c:projet_md_picklayer_bt_ok_onclicked)) (setq aopora-fin (dcl-grid-setcurcell aopora-fin (axedyn-reaccreate pt_tan))) (setq ls_importsources (dcl-grid-setcurcell ls_importsources "Reconstruction des réacteurs des paramètres")) (setq poly-vlatrace (dcl-grid-setcurcell poly-vlatrace 'ls_paramentxy)) (setq projet_md_picklayer (dcl-grid-setcurcell projet_md_picklayer 0)) (setq gvar_3345 (st_rayon gvar_3345 "\nBoucle sur les sources" ls_importsources)) (setq gvar_3345 (st_rayon gvar_3345 'stylepoly-fillcombo aopora-fin)) (setq gvar_3345 (st_rayon gvar_3345 'ls_importsource poly-vlatrace)) (setq gvar_3345 (st_rayon gvar_3345 'c:projet_md_picklayer_bt_ok_onclicked projet_md_picklayer)) (va_pente) (st_linkpath re_yinv))
)

(defun c:projet_pa_mpolydyn_bt_del_onclicked (/ ls_importsources aopora-fin poly-vlatrace projet_md_picklayer gvar_3345)
  (entdel 'c1)
  (setq ls_importsources (in_param gvar_3345 "\nBoucle sur les sources"))
  (setq aopora-fin (in_param gvar_3345 'stylepoly-fillcombo))
  (setq poly-vlatrace (in_param gvar_3345 'ls_importsource))
  nil
  (or (and (and polybib-perpoint (st_blkbase polybib-perpoint 255) (setq projet_md_picklayer (in_param gvar_3345 'c:projet_md_picklayer_bt_ok_onclicked))) (and (st_blkbase polybib-perpoint 0) (ls_ext2 (dcl-grid-addrow (st_axeid polybib-perpoint) aopora-fin) (dcl-grid-addrow (vla-get-name polybib-perpoint) aopora-fin)))) polybib-vtxjoin)
  (setq aopora-fin (ls_atts polybib-perpoint aopora-fin))
  (setq ls_importsources (ls_atts polybib-perpoint ls_importsources))
  (setq poly-vlatrace (ls_atts polybib-perpoint poly-vlatrace))
  (setq projet_md_picklayer (ls_atts polybib-perpoint projet_md_picklayer))
  T
  (setq aopora-fin (ls_atts (st_axeid polybib-perpoint) aopora-fin))
  (setq aopora-fin (ls_atts polybib-perpoint aopora-fin))
  (setq ls_importsources (ls_atts (st_axeid polybib-perpoint) ls_importsources))
  (setq ls_importsources (ls_atts polybib-perpoint ls_importsources))
  (setq poly-vlatrace (ls_atts (vla-get-name polybib-perpoint) poly-vlatrace))
  (setq poly-vlatrace (ls_atts (vla-get-name polybib-perpoint) poly-vlatrace))
  (setq projet_md_picklayer (ls_atts (st_axeid polybib-perpoint) projet_md_picklayer))
  (ls_som0)
  (and (setq projet_md_picklayer (ls_atts polybib-perpoint projet_md_picklayer)) (setq gvar_3345 (st_rayon gvar_3345 "\nBoucle sur les sources" ls_importsources)) (setq gvar_3345 (st_rayon gvar_3345 'stylepoly-fillcombo aopora-fin)) (setq gvar_3345 (st_rayon gvar_3345 'ls_importsource poly-vlatrace)) (setq gvar_3345 (st_rayon gvar_3345 'c:projet_md_picklayer_bt_ok_onclicked projet_md_picklayer)) (va_pente) (st_linkpath re_yinv))
)

(defun c:projet_pa_mpolydyn_st_amont_onselchanged (/ eo_poly arg_2 gvar_1392 ls_importsources pt_pas)
  (entdel 'd)
  (setq gvar_1392 (dcl-grid-addrow eo_poly_2 (polybib-lwvertices 'axedyn-reaccreate projet_pa_polydyn)))
  (setq ls_importsources (in_param gvar_3345 "\nBoucle sur les sources"))
  (setq pt_pas (dcl-grid-addrow polybib-perpoint ls_importsources))
  (or (re_angle 0 eo_poly_2 (ls_props2 gvar_1408)) (re_angle 1 eo_poly_2 (ls_props2 gvar_1408)))
  (bo_invpoly1 gvar_1408 0)
  (bo_invpoly1 gvar_1408 1)
  (re_1 gvar_1392 pt_pas gvar_1409 re_1)
)

(defun c:projet_pa_mpolydyn_st_aval_onselchanged (/ eo_poly arg_2 gvar_1392 poly-vlatrace ls_inters1)
  (entdel 'delta)
  (setq gvar_1392 (dcl-grid-addrow eo_poly_2 (polybib-lwvertices 'axedyn-reaccreate projet_pa_polydyn)))
  (setq poly-vlatrace (in_param gvar_3345 'ls_importsource))
  (setq ls_inters1 (dcl-grid-addrow polybib-perpoint poly-vlatrace))
  (or (re_angle 0 eo_poly_2 (ls_props2 gvar_1409)) (re_angle 1 eo_poly_2 (ls_props2 gvar_1409)))
  (bo_invpoly1 gvar_1409 0)
  (bo_invpoly1 gvar_1409 1)
  (re_1 gvar_1392 ls_inters1 gvar_1408 re_2)
)

(defun mpolydyndial-changeamontaval (arg_1 sqrt h atan)
  nil
  (or (or (re_angle arg_1 'blkpoly-poly) (re_angle arg_1 '(re_x re_y pt_poly re_anglepoly re_angle))) polybib-vtxjoin)
  (re_hauteur atan nil)
  (re_hauteur atan polybib-vtxjoin)
  (if (en_txt sqrt)
    (progn
      (vlax-invoke atan 'pt_11)
    )
    (progn
      (vlax-invoke atan 'eo_txt)
    )
  )
  (re_hauteur atan polybib-vtxjoin)
  (if (re_angle (undobib-start sqrt) 'es_ext)
    (progn
      (vlax-invoke atan 'pt_11)
    )
    (progn
      (vlax-invoke atan 'eo_txt)
    )
  )
)

(defun c:projet_pa_mpolydyn_bt_amont_onclicked (/ iang h)
  (setq iang "\nBoucle sur les sources")
  (setq h gvar_1409)
  (ang iang h)
)

(defun mpolydyndial-selectamontaval (iang h / set gvar_1392 gvar_1354 gvar_3345)
  (entdel '(bo_inv d ang iang))
  (setq set (in_param gvar_3345 iang))
  (setq gvar_1392 (dcl-grid-addrow (ls_props2 h) (polybib-lwvertices 'axedyn-reaccreate projet_pa_polydyn)))
  (or (re_angle gvar_1392 'blkpoly-poly) (re_angle gvar_1392 '(re_x re_y pt_poly re_anglepoly re_angle)))
  (setq gvar_1354 (va_param 'blkpoly-wcs2wxy))
  (setq gvar_1354 (st_visi 'acos))
  (setq set (row gvar_1354 polybib-perpoint set))
  (setq gvar_3345 (st_rayon gvar_3345 iang set))
  (ls_som0)
)

(defun c:projet_pa_mpolydyn_bt_aval_onclicked (/ iang h)
  (setq iang 'ls_importsource)
  (setq h gvar_1408)
  (ang iang h)
)

(defun c:projet_pa_mpolydyn_bt_apply_onclicked (/ gvar_1351 *ls_styles* pt_absdyn ls_importsources poly-vlatrace projet_md_picklayer gvar_3345 gvar_1349 gvar_1348 re_2max)
  (entdel '(st_style en_ref en_polydyn st_nom))
  (setq ls_importsources (in_param gvar_3345 "\nBoucle sur les sources"))
  (setq poly-vlatrace (in_param gvar_3345 'ls_importsource))
  (setq projet_md_picklayer (in_param gvar_3345 'c:projet_md_picklayer_bt_ok_onclicked))
  (setq projet_md_picklayer (row pt_absdyn polybib-perpoint projet_md_picklayer))
  (setq gvar_3345 (st_rayon gvar_3345 'c:projet_md_picklayer_bt_ok_onclicked projet_md_picklayer))
  (setq gvar_1349 (dcl-grid-addrow gvar_1351 (polybib-lwvertices 'axedyn-reaccreate projet_pa_polydyn)))
  (setq gvar_1348 (dcl-grid-addrow *ls_styles* (polybib-lwvertices 'axedyn-reaccreate projet_pa_polydyn)))
  (if (and (dcl-grid-clear gvar_1417) polybib-perpoint (st_blkbase polybib-perpoint 255) (st_blkbase (setq gvar_1351 (ls_props2 gvar_1409)) 255) (st_blkbase (setq *ls_styles* (ls_props2 gvar_1408)) 255) (setq pt_absdyn (axe-set re_offsetmod)) (laybib-newlay gvar_1349 (es_ext "Reconstruction des réacteurs des paramètres" 'ls_paramentxy 're_rayii '(lambda (ls_elem) (= "H" (listbib-key ls_elem "st_type"))))))
    (progn
      (setq ls_importsources (row gvar_1349 polybib-perpoint ls_importsources))
      (setq gvar_3345 (st_rayon gvar_3345 "\nBoucle sur les sources" ls_importsources))
    )
  )
  (if (laybib-newlay gvar_1348 (es_ext "Reconstruction des réacteurs des paramètres" 'ls_paramentxy 're_rayii '(lambda (ls_elem) (= "H" (listbib-key ls_elem "st_type")))))
    (progn
      (setq poly-vlatrace (row gvar_1348 polybib-perpoint poly-vlatrace))
      (setq gvar_3345 (st_rayon gvar_3345 'ls_importsource poly-vlatrace))
    )
  )
  (va_pente)
  (ls_group geombib-getinsideangle re_2max 255)
  T
  (setq re_2max polybib-perpoint)
  (ls_som0)
  (st_linkpath re_yinv)
)

(defun c:projet_pa_mpolydyn_onclose (/ blkpoly-proj st_grouphandle polydyn-edit-fillgrid gvar_1397)
  (polybib-perpoint polydyn-edit-fillgrid nil)
  (sihpp-list gvar_1397)
  (setq polydyn-edit-fillgrid nil)
  (setq gvar_1397 nil)
  (ls_som0)
)

(defun mpolydyn-ext (arg_1 arg_2 / local_2 axedyn-list gvar_1341 *ls_typeabs*)
  (entdel '*ls_typedec*)
  (setq axedyn-list (axedyn-reaccreate arg_1))
  (setq gvar_1341 (dcl-grid-addrow 2 axedyn-list))
  (setq local_2 (eo_polyabs arg_1))
  (foreach *ls_typeabs* local_2
    (if (repdyn-getpoint (dcl-grid-addrow 2 *ls_typeabs*) gvar_1341)
      (progn
        (setq axedyn-list *ls_typeabs*)
        (setq gvar_1341 (dcl-grid-addrow 2 *ls_typeabs*))
      )
    )
  )
  axedyn-list
)

(defun c:projet_md_selblk_oninitialize ()
  (st_value gvar_1331 (*reactor2*))
  (jsonbib-json2list projet_pa_polydyn_grille_offsets)
  T
  (re_hauteur projet_pa_polydyn_re_absmod projet_pa_polydyn_re_offsetmod)
  (re_hauteur projet_pa_polydyn_la_type gvar_1325)
  (and dcl-listbox-clear (bo_lctabs projet_pa_polydyn_bt_enregistrer dcl-listbox-clear) (laybib-newlay dcl-listbox-clear (*reactor2*)) (pt_poly projet_pa_polydyn_grille_offsets dcl-listbox-clear) (cmd gvar_1331 dcl-listbox-clear))
)

(defun c:projet_md_selblk_ls_blk_onselchanged (/ eo_poly arg_2)
  (bo_lctabs projet_pa_polydyn_bt_enregistrer (dcl-grid-addrow eo_poly_2 (*reactor2*)))
  (pt_poly projet_pa_polydyn_grille_offsets (dcl-grid-addrow eo_poly_2 (*reactor2*)))
)

(defun c:projet_md_selblk_bt_cancel_onclicked (/ dcl-listbox-clear)
  (re_abs1 *st_nodeid* 20)
)

(defun c:projet_md_selblk_bt_ok_onclicked (/ dcl-listbox-clear)
  (setq dcl-listbox-clear (errbib-catchapply projet_pa_polydyn_bt_enregistrer))
  (if (laybib-newlay dcl-listbox-clear (*reactor2*))
    (progn
      (re_abs1 *st_nodeid* 10)
    )
    (progn
      (bordyn-inters '(ls_som st_abs st_type re_absmod st_offset re_offsetmod))
    )
  )
)

(defun c:projet_md_selblk_ls_blk_ondblclicked ()
  (re_abs1 *st_nodeid* 10)
)

(defun c:projet_md_selblk_bt_file_onclicked ()
  (ls_ptinint '*ls_som* 'close)
)

(defun c:projet_md_selblk_bt_pick_onclicked ()
  (re_abs1 *st_nodeid* 1)
)

(defun polydyn-list ()
  (axedyn-setrayext 'ls_blks)
)

(defun polydyn-get (en_rayon)
  (re_courant 'ls_blks en_rayon)
)

(defun polydyn-set (en_rayon arg_2)
  (fas-rtos3 'ls_blks en_rayon arg_2)
)

(defun polydyn-pt2numnode (arg_1 arg_2 listbib-substlist)
  (polydyn-dialfilledit listbib-substlist (palbib-init arg_1 arg_2))
)

(defun polydyn-popgo (en_rayon / gvar_2607 gvar_1306 blkbib-getvisinames ls_axe polybib_geom-bulge2radius gvar_3155 gvar_3162 projet_md_metprop_cb_layer gvar_2537 dcl-form-close gvar_3265 ls_propsdescs)
  (entdel '(st_syle ls_som en_polydyn en_ref st_nom))
  (setq gvar_2607 nil)
  (if gvar_3345
    (progn
      (setq gvar_1306 gvar_3345)
    )
    (progn
      (setq gvar_1306 (st_special en_rayon))
    )
  )
  T
  (setq blkbib-getvisinames (in_param gvar_1306 '(lambda (ls_ent) (listbib-key ls_ent "st_layer"))))
  (setq ls_axe (in_param gvar_1306 'dcl-form-show))
  (setq polybib_geom-bulge2radius (pt_proj ls_axe))
  (setq polybib_geom-bulge2radius (dcl-grid-setcurcell polybib_geom-bulge2radius (groupbib-list 70 128)))
  (setq gvar_3265 (in_param gvar_1306 'ls_importfilters))
  (if (and (setq gvar_3155 'chemdyn-bordtrace) (setq gvar_3162 (in_param gvar_1306 'va_point)) (setq projet_md_metprop_cb_layer (hachbib-vtxs2hach gvar_3162)) (setq gvar_2537 (re_ray projet_md_metprop_cb_layer)) (fas-polar1 gvar_2537) (setq gvar_3155 "\nMise à jour en cours..") (setq dcl-form-close (*va_abs* gvar_2537 blkbib-getvisinames)) (setq gvar_2607 polybib-vtxjoin) gvar_2607)
    (progn
      (if (and gvar_3265 (setq ls_propsdescs (re_ray gvar_3265)) (fas-polar1 ls_propsdescs))
        (progn
          (sssetfirst ls_propsdescs dcl-form-close polybib_geom-bulge2radius)
          (setq gvar_3155 '*va_abs*)
          (setq gvar_3155 nil)
        )
        (progn
          (ls_layers en_rayon gvar_1306)
          (setq gvar_3155 '(ls_som st_abs va_abs re_absmod en_av va_av pt_av))
          (setq ls_propsdescs (*en_ray* dcl-form-close polybib_geom-bulge2radius))
          (setq gvar_3265 (fas-1- ls_propsdescs))
          (setq gvar_1306 (st_rayon gvar_1306 'ls_importfilters gvar_3265))
          (setq gvar_3155 '(ls_som st_offset va_offset re_offsetmod re_off))
          (setq gvar_3155 nil)
        )
      )
    )
  )
  (if gvar_3155
    (progn
      (ls_som0 gvar_3155)
    )
  )
  (setq gvar_3155 nil)
  gvar_3265
)

(defun polydyn-makelists (/ local_0 gvar_2537 re_offd blkbib-getvisinames re_u pt_d listbib-substlist pt_dp gvar_3385 gvar_3388 polydynraccord polybib-subpolyoff ls_prop metquant-dial-gr_prixfill polybib-subpolyoff2)
  (entdel '(st_type in_som re_absd re_offd pt_d re_absf pt_f ls_vtx))
  (setq gvar_2537 (re_ray (hachbib-vtxs2hach (in_param gvar_3345 'va_point))))
  (setq re_offd (re_ray (in_param gvar_3345 'ls_importfilters)))
  (setq blkbib-getvisinames (in_param gvar_3345 '(lambda (ls_ent) (listbib-key ls_ent "st_layer"))))
  (setq re_u (es_ext))
  (setq pt_d (es_ext))
  (setq listbib-substlist (es_ext))
  (setq pt_dp 0)
  (setq local_0 blkbib-getvisinames)
  nil
  (foreach gvar_3385 local_0
    (setq gvar_3388 (re_offf gvar_2537 blkbib-getvisinames pt_dp))
    (setq polydynraccord (pt_fp gvar_2537 blkbib-getvisinames pt_dp))
    (setq polybib-subpolyoff (ls_param gvar_2537 gvar_3388))
    (setq ls_prop (fas-getvar2 gvar_2537 polybib-subpolyoff))
    (setq metquant-dial-gr_prixfill (fas-getvar3 polybib-subpolyoff (dcl-grid-addrow ls_prop (repdyn-isrep gvar_3236 'repdyn-isrep)) polydynraccord))
    (setq polybib-subpolyoff2 (st_param re_offd metquant-dial-gr_prixfill))
    (setq re_u (dcl-grid-setcurcell re_u gvar_3388))
    (setq pt_d (dcl-grid-setcurcell pt_d polydynraccord))
    (setq listbib-substlist (dcl-grid-setcurcell listbib-substlist polybib-subpolyoff2))
    (setq pt_dp (st_axeid pt_dp))
  )
)

(defun polydyn-makesom (polybib-subpolybisinv / arg_2 arg_3 arg_4 repdyn-go polydyn-pt2numnode ls_ans arg_8 arg_9)
  (es_ext (groupbib-list 'st_type polybib-subpolybisinv) (groupbib-list '(en_polydyn en_ref ls_soms ls_som st_type st_abs st_offset re_absmod re_offsetmod va_abs) arg_2) (groupbib-list "Milieu" arg_3) (groupbib-list '(lambda (ls_rep) (cons (car ls_rep) (if (or (not (listbib-key (cdr ls_rep) "st_nom")) (= "" (listbib-key (cdr ls_rep) "st_nom"))) (car ls_rep) (listbib-key (cdr ls_rep) "st_nom")))) arg_4) (groupbib-list 'ls_txt repdyn-go) (groupbib-list "Liste" polydyn-pt2numnode) (groupbib-list " [Liste des PolyDyn] : " ls_ans) (groupbib-list "\nDistance par rapport au point précédent : " arg_8) (groupbib-list 're_rel arg_9))
)

(defun polydyn-tracerep (re_offd listbib-substlist arg_3 re_u / local_4 gvar_3388 polybib-subpolyoff polydynraccord gvar_1255 dcl-form-close st_2)
  (entdel '(ans flag))
  (setq re_offd 0)
  (setq local_4 re_u)
  (foreach gvar_3388 local_4
    (setq polybib-subpolyoff (ls_param arg_3 gvar_3388))
    (setq polydynraccord (dcl-grid-addrow re_offd re_offd))
    (setq gvar_1255 (re_rel arg_3 gvar_3388 polydynraccord))
    (setq re_offd (st_axeid re_offd))
    (setq dcl-form-close (es_ext (es_ext (groupbib-list 10 polybib-subpolyoff)) (es_ext (groupbib-list 10 gvar_1255))))
    (setq st_2 (dcl-grid-setcurcell st_2 (*en_ray* dcl-form-close (es_ext (groupbib-list 62 4) (groupbib-list 8 'st_btn)))))
  )
  st_2
)

(defun c:polycc (/ gvar_1252 *ls_elems* gvar_2200 *ls_parents* gvar_3244 gvar_3242 dcl-grid-setcellstyle gvar_1864 dcl-form-close)
  (setq gvar_1252 "\nDécalage par rapport à l'origine : ")
  (setq *ls_elems* '(ls_type en_elem))
  (setq gvar_2200 (blkpoly-set (fas-polar1 ls_state)))
  (setq *ls_parents* (blkpoly-set (fas-polar1 gvar_1861)))
  (setq gvar_3244 (in_param (fas-1- gvar_2200) 10))
  (setq gvar_3242 (in_param (axedyn-reaccreate *ls_parents*) 10))
  (setq dcl-grid-setcellstyle (fas-getvar2 ls_state gvar_3244))
  (setq gvar_1864 (fas-getvar2 gvar_1861 gvar_3242))
  (setq dcl-form-close (projet_pa_projet_ar_projet gvar_3244 gvar_3242 dcl-grid-setcellstyle gvar_1864 gvar_1252 *ls_elems*))
  (*en_ray* dcl-form-close nil)
)

(defun polydyncc (arg_1 arg_2 dcl-grid-setcellstyle arg_4 *ls_elems* / in_cellnum in_state inc local_3 gvar_1815 gvar_1814 ls_type en_elem pt_ref ls_prop projexp-addelement racdyn-list repdyn-list resdyn-list gvar_1239 bordyn-list projet_md_selblk_bt_pick gvar_2705 gvar_1234 sihlin-list dcl-form-close)
  (entdel 'dcl-tree-selectitem)
  (setq gvar_1815 (*ls_petypes* arg_1 dcl-grid-setcellstyle arg_2))
  (setq gvar_1814 (*ls_petypes* arg_2 in_state arg_1))
  (setq ls_type (fas-getvar3 arg_1 (dcl-grid-addrow dcl-grid-setcellstyle (repdyn-isrep gvar_3236 2)) (ls_visient gvar_1815 arg_4)))
  (setq en_elem (fas-getvar3 arg_2 (dcl-grid-addrow in_state (repdyn-isrep gvar_3236 2)) (ls_visient gvar_1814 *ls_elems*)))
  (setq pt_ref (pt_ref arg_1 arg_2))
  (setq ls_prop (blkbib-getvisient arg_1 arg_2))
  (setq projexp-addelement (entib-handle2ename (repdyn-isrep pt_ref 'repdyn-isrep (in_closed (dcl-grid-addrow dcl-grid-setcellstyle ls_prop)))))
  (setq racdyn-list (fas-getvar3 ls_type (dcl-grid-addrow in_state (repdyn-isrep gvar_3236 2)) (ls_visient gvar_1814 arg_4)))
  (setq repdyn-list (fas-getvar3 ls_type (dcl-grid-addrow in_state (repdyn-isrep gvar_3236 2)) (ls_visient '(va_point re_abs pt_base pt_1 pt_2 re_abs1 re_abs2) gvar_1814 arg_4)))
  (setq resdyn-list (ls_parents racdyn-list arg_2 repdyn-list (fas-getvar3 repdyn-list (dcl-grid-addrow (blkbib-getvisient racdyn-list arg_2) (repdyn-isrep gvar_3236 2)) 'en_poly) nil))
  (setq gvar_1239 (ls_parents ls_type resdyn-list arg_2 (fas-getvar3 arg_2 (dcl-grid-addrow in_state (repdyn-isrep gvar_3236 2)) 'en_poly) nil))
  (setq bordyn-list (pt_ref gvar_1239 arg_2))
  (or (or (or (and (re_angle arg_4 'ha_poly) (re_angle *ls_elems* 'ha_poly)) (st_blkbase arg_4 projexp-addelement)) (st_blkbase *ls_elems* bordyn-list)) polybib-vtxjoin)
  (and (and (and (and (st_blkbase gvar_1815 'ha_poly) (st_blkbase gvar_1814 'ha_poly)) (and (repdyn-getpoint gvar_1815 'ha_poly) (repdyn-getpoint gvar_1814 'ha_poly))) (and (st_blkbase gvar_1815 'ha_poly) (repdyn-getpoint gvar_1814 'ha_poly))) (and (repdyn-getpoint gvar_1815 'ha_poly) (st_blkbase gvar_1814 'ha_poly)))
  (setq projet_md_selblk_bt_pick (fas-1- (chemdyn-list ls_type en_elem arg_4 *ls_elems*)))
  (setq projet_md_selblk_bt_pick (axedyn-reaccreate (chemdyn-list ls_type en_elem arg_4 *ls_elems*)))
  (setq projet_md_selblk_bt_pick (fas-1- (blkpoly-list ls_type en_elem arg_4 *ls_elems*)))
  (setq projet_md_selblk_bt_pick (axedyn-reaccreate (blkpoly-list ls_type en_elem arg_4 *ls_elems*)))
  (setq gvar_2705 (axedyn-reaccreate projet_md_selblk_bt_pick))
  (setq in_cellnum (fas-1- projet_md_selblk_bt_pick))
  (setq ls_prop (blkbib-getvisient gvar_2705 in_cellnum))
  (if (st_blkbase gvar_1815 'ha_poly)
    (progn
      (setq gvar_1234 (taldyn-list ls_type ls_prop dcl-grid-setcellstyle arg_4))
    )
    (progn
      (setq gvar_1234 (taldyn-list ls_type dcl-grid-setcellstyle ls_prop arg_4))
    )
  )
  (if (st_blkbase gvar_1814 'ha_poly)
    (progn
      (setq sihlin-list (taldyn-list en_elem in_state ls_prop *ls_elems*))
    )
    (progn
      (setq sihlin-list (taldyn-list en_elem ls_prop in_state *ls_elems*))
    )
  )
  (setq dcl-form-close (es_ext (es_ext (groupbib-list 10 arg_1) (groupbib-list 42 (ls_visient '(va_point re_abs pt_base pt_1 pt_2 re_abs1 re_abs2) gvar_1815 (dcl-grid-addrow 1 gvar_1234)))) (es_ext (groupbib-list 10 gvar_2705) (groupbib-list 40 0)) (es_ext (groupbib-list 10 in_cellnum) (groupbib-list 42 (ls_visient '(va_point re_abs pt_base pt_1 pt_2 re_abs1 re_abs2) gvar_1814 (dcl-grid-addrow 1 sihlin-list)))) (es_ext (groupbib-list 10 arg_2) (groupbib-list 40 0))))
  (setq en_elem gvar_1239)
  (setq ls_prop (st_syle (blkbib-getvisient ls_type en_elem) (repdyn-isrep gvar_3236 'repdyn-isrep)))
  (if (st_blkbase gvar_1815 'ha_poly)
    (progn
      (setq gvar_1234 (taldyn-list ls_type ls_prop (dcl-grid-addrow dcl-grid-setcellstyle gvar_3236) arg_4))
    )
    (progn
      (setq gvar_1234 (taldyn-list ls_type dcl-grid-setcellstyle ls_prop arg_4))
    )
  )
  (if (st_blkbase gvar_1814 'ha_poly)
    (progn
      (setq sihlin-list (taldyn-list en_elem in_state ls_prop bordyn-list))
    )
    (progn
      (setq sihlin-list (taldyn-list en_elem (dcl-grid-addrow ls_prop gvar_3236) in_state bordyn-list))
    )
  )
  (setq dcl-form-close (es_ext (es_ext (groupbib-list 10 arg_1) (groupbib-list 42 (ls_visient '(va_point re_abs pt_base pt_1 pt_2 re_abs1 re_abs2) gvar_1815 (dcl-grid-addrow 1 gvar_1234)))) (es_ext (groupbib-list 10 resdyn-list) (groupbib-list 42 (ls_visient '(va_point re_abs pt_base pt_1 pt_2 re_abs1 re_abs2) gvar_1814 (dcl-grid-addrow 1 sihlin-list)))) (es_ext (groupbib-list 10 arg_2) (groupbib-list 40 0))))
  (setq ls_type (fas-getvar3 arg_1 (dcl-grid-addrow dcl-grid-setcellstyle (repdyn-isrep gvar_3236 2)) (ls_visient gvar_1815 projexp-addelement)))
  (if (repdyn-getpoint gvar_1815 'ha_poly)
    (progn
      (setq gvar_1234 (taldyn-list ls_type dcl-grid-setcellstyle (st_syle dcl-grid-setcellstyle (st_key arg_1 ls_type arg_2)) projexp-addelement))
    )
    (progn
      (setq gvar_1234 (taldyn-list ls_type dcl-grid-setcellstyle (st_syle dcl-grid-setcellstyle (st_key arg_1 ls_type arg_2)) projexp-addelement))
    )
  )
  (setq dcl-form-close (es_ext (es_ext (groupbib-list 10 arg_1) (groupbib-list 42 (ls_visient '(va_point re_abs pt_base pt_1 pt_2 re_abs1 re_abs2) gvar_1815 (dcl-grid-addrow 1 gvar_1234)))) (es_ext (groupbib-list 10 arg_2) (groupbib-list 40 0))))
  (setq dcl-form-close (es_ext (es_ext (groupbib-list 10 arg_1) (groupbib-list 40 0)) (es_ext (groupbib-list 10 arg_2) (groupbib-list 40 0))))
  dcl-form-close
)

(defun polycc-side (entlast ls_prop / en_parent ls_parent ls_ent st_id st_txt local_2 gvar_3244 gvar_3242)
  (entdel 'en_parent)
  (setq gvar_3244 (fas-getvar3 entlast (st_syle ls_prop (repdyn-isrep gvar_3236 2)) 'en_poly))
  (setq gvar_3242 (fas-getvar3 entlast (dcl-grid-addrow ls_prop (repdyn-isrep gvar_3236 2)) 'en_poly))
  (if (repdyn-getpoint (pt_ref gvar_3244 en_parent) (pt_ref gvar_3242 en_parent))
    (progn
      '(va_point re_abs pt_base pt_1 pt_2 re_abs1 re_abs2)
    )
    (progn
      'en_poly
    )
  )
)

(defun polycc-tanext (arg_1 *st_petype* *st_peid* / eo_ent st_type st_id ha_ref st_ldataname local_1 ha_zoom projet_pa_projet_btn_zoom projet_pa_projet_btn_edit projet_pa_projet_btn_delete)
  (entdel "OC-Polyligne")
  (setq *st_peid* (pt_ref arg_1 *st_petype*))
  (setq ha_zoom (dcl-grid-addrow *st_petype* *st_peid*))
  (setq projet_pa_projet_btn_zoom (en_zoom (dcl-grid-addrow (ls_visient *st_peid* *st_peid*) (ls_visient ha_zoom ha_zoom))))
  (setq projet_pa_projet_btn_edit (projet_pa_projet_btn_update projet_pa_projet_btn_zoom ha_zoom))
  (setq projet_pa_projet_btn_delete (blkbib-getvisient arg_1 *st_petype*))
  (es_ext (es_ext (fas-getvar3 arg_1 (st_syle projet_pa_projet_btn_delete projet_pa_projet_btn_edit) *st_petype*) (fas-getvar3 *st_petype* (st_syle projet_pa_projet_btn_delete projet_pa_projet_btn_edit) *st_peid*)) (es_ext (fas-getvar3 arg_1 (dcl-grid-addrow projet_pa_projet_btn_delete projet_pa_projet_btn_edit) *st_petype*) (fas-getvar3 *st_petype* (dcl-grid-addrow projet_pa_projet_btn_delete projet_pa_projet_btn_edit) *st_peid*)))
)

(defun polycc-tanint (arg_1 *st_petype* *st_peid* / eo_ent st_type st_id ha_ref st_ldataname local_1 projet_pa_projet_btn_delete projet_pa_projet_btn_edit)
  (entdel 'projet_pa_projet_gr_props)
  (if (st_blkbase *st_petype* *st_peid*)
    (progn
      (polybib-lwvertices 'projexp-affprops '(st_key st_type st_id) (es_ext *st_petype* arg_1 *st_peid* *st_petype* polybib-vtxjoin))
    )
  )
  (if (st_blkbase (setq *st_peid* (pt_ref arg_1 *st_petype*)) (st_syle *st_petype* *st_peid*))
    (progn
      (setq projet_pa_projet_btn_delete (blkbib-getvisient arg_1 *st_petype*))
      (setq projet_pa_projet_btn_edit (dcl-tree-isitemexpanded (repdyn-isrep (st_syle *st_petype* *st_peid*) *st_peid*)))
      (if re_cotechem
        (progn
          (es_ext (es_ext (fas-getvar3 *st_petype* (st_syle projet_pa_projet_btn_delete projet_pa_projet_btn_edit) (dcl-grid-addrow *st_peid*)) (fas-getvar3 arg_1 (st_syle projet_pa_projet_btn_delete projet_pa_projet_btn_edit) *st_petype*)) (es_ext (fas-getvar3 *st_petype* (dcl-grid-addrow projet_pa_projet_btn_delete projet_pa_projet_btn_edit) (dcl-grid-addrow *st_peid*)) (fas-getvar3 arg_1 (dcl-grid-addrow projet_pa_projet_btn_delete projet_pa_projet_btn_edit) *st_petype*)))
        )
        (progn
          (es_ext (es_ext (fas-getvar3 arg_1 (st_syle projet_pa_projet_btn_delete projet_pa_projet_btn_edit) *st_petype*) (fas-getvar3 *st_petype* (st_syle projet_pa_projet_btn_delete projet_pa_projet_btn_edit) (dcl-grid-addrow *st_peid*))) (es_ext (fas-getvar3 arg_1 (dcl-grid-addrow projet_pa_projet_btn_delete projet_pa_projet_btn_edit) *st_petype*) (fas-getvar3 *st_petype* (dcl-grid-addrow projet_pa_projet_btn_delete projet_pa_projet_btn_edit) (dcl-grid-addrow *st_peid*))))
        )
      )
    )
    (progn
      nil
    )
  )
)

(defun polydyn-edit-fillgrid (en_rayon / local_1 gvar_2537 blkbib-getvisinames pt_dp gvar_3385)
  (entdel 'bo_ent)
  (*en_ins* aosup-go)
  (setq gvar_2537 (re_ray (hachbib-vtxs2hach (in_param gvar_3345 'va_point))))
  (setq blkbib-getvisinames (in_param gvar_3345 '(lambda (ls_ent) (listbib-key ls_ent "st_layer"))))
  (setq pt_dp 0)
  (setq local_1 blkbib-getvisinames)
  (foreach gvar_3385 local_1
    (eo_blkpop aosup-go (dcl-control-setenabled (st_axeid pt_dp)) (in_param gvar_3385 'st_type) (in_param gvar_3385 '(en_polydyn en_ref ls_soms ls_som st_type st_abs st_offset re_absmod re_offsetmod va_abs)) (eo_blkbase (re_offf gvar_2537 blkbib-getvisinames pt_dp) 2 2) (in_param gvar_3385 'ls_txt) (eo_blkbase (pt_fp gvar_2537 blkbib-getvisinames pt_dp) 2 2))
    (setq pt_dp (st_axeid pt_dp))
  )
  (ls_som0)
)

(defun c:projet_pa_polydyn_grille_offsets_onselchanged (/ eq netbib-purgeblock ls_paramwcs)
  (entdel "Nom")
  (if (st_blkbase eq_2 255)
    (progn
      (bo_ent eq_2)
    )
  )
  (vlax-vla-object->ename dcl-tree-deleteitem polybib-vtxjoin)
  (vlax-vla-object->ename gvar_1197 polybib-vtxjoin)
  (vlax-vla-object->ename gvar_1196 polybib-vtxjoin)
  (vlax-vla-object->ename getkword polybib-vtxjoin)
  (vlax-vla-object->ename gvar_1189 polybib-vtxjoin)
  (vlax-vla-object->ename gvar_1188 polybib-vtxjoin)
  (re_hauteur st_nomold ls_paramwcs)
  (re_hauteur gvar_1197 ls_paramwcs)
  (setq ls_paramwcs (repdyn-getpoint eq_2 (vla-get-name (st_ray2 (in_param gvar_3345 '(lambda (ls_ent) (listbib-key ls_ent "st_layer")))))))
  (ls_som0)
)

(defun c:projet_pa_polydyn_bt_supprimer_onclicked (/ local_0 gvar_3169 blkbib-getvisinames gvar_1268 gvar_3345 re_u listbib-substlist vlax-curve-isclosed)
  (entdel 'aopora-rename)
  (if (and (dcl-grid-clear gvar_1272) (setq gvar_3169 (axedyn-reaccreate (blkpoly-ls_entsnew aosup-go))) (setq blkbib-getvisinames (in_param gvar_3345 '(lambda (ls_ent) (listbib-key ls_ent "st_layer")))) (st_blkbase (st_ray2 blkbib-getvisinames) 2) (st_blkbase gvar_3169 255))
    (progn
      (setq blkbib-getvisinames (ls_atts gvar_3169 blkbib-getvisinames))
      (setq local_0 vlax-curve-isclosed)
      (foreach gvar_1268 local_0
        (column gvar_1268)
      )
      (ls_layers re_yinv gvar_3345)
      (listbib-remove_doubles re_yinv)
      (ha_rep)
      (setq gvar_3345 (st_rayon gvar_3345 '(lambda (ls_ent) (listbib-key ls_ent "st_layer")) blkbib-getvisinames))
      (setq re_u (es_ext))
      (setq listbib-substlist (es_ext))
      (setq vlax-curve-isclosed (ha_rep re_offd listbib-substlist gvar_2537 re_u))
      (if (dcl-grid-clear gvar_1272)
        (progn
          (boxlib-listbox re_yinv)
        )
        (progn
          nil
        )
      )
    )
    (progn
      nil
    )
  )
)

(defun c:polydyn_pal_polydyn_grille_offsets_ondblclicked (/ eq netbib-purgeblock)
  (if (st_blkbase eq_2 255)
    (progn
      (pt_c2 (dcl-grid-addrow eq_2 vlax-curve-isclosed) polybib-vtxjoin)
    )
    (progn
      nil
    )
  )
)

(defun polydyn-dialfilledit (eq / dcl-tree-setitemlabel gvar_1183 gvar_1266 polybib-subpolybisinv gvar_1265 repdyn-go ls_ans gvar_3162 projet_md_metprop_cb_layer gvar_2537 gvar_3388 blkpoly-get gvar_1180 gvar_1252 *ls_elems* gvar_1171)
  (entdel '(ls_props projexp-affpropsaxe projexp-affpropspolydyn projexp-affpropsracdyn projexp-affpropsdetdyn projexp-affpropschemdyn))
  (if dcl-tree-setitemlabel
    (progn
      (ls_soms (dcl-grid-addrow dcl-tree-setitemlabel vlax-curve-isclosed) 62 4)
      (polybib-perpoint (dcl-grid-addrow dcl-tree-setitemlabel vlax-curve-isclosed) nil)
      (st_grouphandle nil nil)
    )
  )
  (ls_soms (dcl-grid-addrow dcl-tree-setitemlabel vlax-curve-isclosed) 62 6)
  (polybib-perpoint (dcl-grid-addrow dcl-tree-setitemlabel vlax-curve-isclosed) polybib-vtxjoin)
  (st_grouphandle nil (pt_ptp1 (dcl-grid-addrow dcl-tree-setitemlabel vlax-curve-isclosed)))
  (vlax-invoke in_ext (geombib-raccordmax "Style" (dcl-control-setenabled (st_axeid eq))))
  (sihpp-list gvar_1180)
  (boxlib-optionbox gvar_1180 4)
  (bo_invpoly1 gvar_1197 (laybib-newlay polybib-subpolybisinv (polybib-lwvertices 'axedyn-reaccreate gvar_1203)))
  (vlax-vla-object->ename gvar_1178 T)
  (vlax-vla-object->ename projexp-affpropspolydyn T)
  (vlax-vla-object->ename gvar_1176 (odclbib-fillcombo polybib-subpolybisinv 'dcl-tree-getnextsiblingitem))
  (vlax-vla-object->ename gvar_1175 (odclbib-fillcombo polybib-subpolybisinv 'dcl-tree-getnextsiblingitem))
  (setq dcl-tree-setitemlabel eq)
  (setq gvar_1183 (dcl-grid-addrow eq (in_param gvar_3345 '(lambda (ls_ent) (listbib-key ls_ent "st_layer")))))
  (setq gvar_1266 (in_param gvar_1183 '(en_polydyn en_ref ls_soms ls_som st_type st_abs st_offset re_absmod re_offsetmod va_abs)))
  (setq polybib-subpolybisinv (en_polyabs gvar_1183 'st_type "Croisée "))
  (setq gvar_1265 (in_param gvar_1183 '(lambda (ls_rep) (cons (car ls_rep) (if (or (not (listbib-key (cdr ls_rep) "st_nom")) (= "" (listbib-key (cdr ls_rep) "st_nom"))) (car ls_rep) (listbib-key (cdr ls_rep) "st_nom"))))))
  (setq repdyn-go (in_param gvar_1183 'ls_txt))
  (setq ls_ans (in_param gvar_1183 " [Liste des PolyDyn] : "))
  (setq gvar_3162 (in_param gvar_3345 'va_point))
  (setq projet_md_metprop_cb_layer (hachbib-vtxs2hach gvar_3162))
  (setq gvar_2537 (re_ray projet_md_metprop_cb_layer))
  (setq gvar_3388 (re_offf gvar_2537 (in_param gvar_3345 '(lambda (ls_ent) (listbib-key ls_ent "st_layer"))) eq))
  (setq blkpoly-get (ls_param gvar_2537 gvar_3388))
  (setq gvar_1180 (projexp-affpropsaxe gvar_2537 blkpoly-get 'odclbib-treegetchild nil nil nil))
  (or (or (or (or (or (odclbib-fillcombo polybib-subpolybisinv '(re_x re_y pt_poly re_anglepoly re_angle)) (odclbib-fillcombo polybib-subpolybisinv 'dcl-tree-getnextsiblingitem)) (or (odclbib-fillcombo polybib-subpolybisinv '(re_x re_y pt_poly re_anglepoly re_angle)) (odclbib-fillcombo polybib-subpolybisinv 'dcl-tree-getnextsiblingitem))) (odclbib-fillcombo polybib-subpolybisinv 'dcl-tree-getnextsiblingitem)) (odclbib-fillcombo polybib-subpolybisinv '(re_x re_y pt_poly re_anglepoly re_angle))) polybib-vtxjoin)
  (setq gvar_1252 'ha_poly)
  (setq *ls_elems* 'ha_poly)
  (setq gvar_1252 (en_polyabs gvar_1183 "Référence 2" 'repdyn-isrep))
  (bo_lctabs projexp-affpropspolydyn (eo_blkbase gvar_1252 2 2))
  (bo_lctabs gvar_1175 (eo_blkbase *ls_elems* 2 2))
  (bo_invpoly1 gvar_1196 (laybib-newlay gvar_1266 (polybib-lwvertices 'axedyn-reaccreate gvar_1201)))
  (setq gvar_1252 (en_polyabs gvar_1183 "Référence 2" 'repdyn-isrep))
  (setq *ls_elems* (en_polyabs gvar_1183 "Rayon" 'repdyn-isrep))
  (or (or (re_angle gvar_1266 'blkpoly-poly) (re_angle gvar_1266 '(re_x re_y pt_poly re_anglepoly re_angle))) polybib-vtxjoin)
  (re_hauteur projexp-affpropsracdyn nil)
  (re_hauteur projexp-affpropsracdyn polybib-vtxjoin)
  (vlax-invoke projexp-affpropsracdyn (geombib-raccordmax 'en_txt (in_param gvar_1183 "Milieu")))
  (re_hauteur projexp-affpropsracdyn polybib-vtxjoin)
  (vlax-invoke projexp-affpropsracdyn 'pt_11)
  (bo_invpoly1 getkword (laybib-newlay repdyn-go (polybib-lwvertices 'axedyn-reaccreate gvar_1199)))
  (bo_lctabs gvar_1189 (eo_blkbase gvar_1265 2 2))
  (bo_lctabs gvar_1188 (eo_blkbase ls_ans 2 2))
  (setq gvar_1171 (blkpoly-ls_entsnew aosup-go))
  (or (or (or (or (re_angle (re_x gvar_1171) 1) (re_angle (re_x gvar_1171) 2)) (re_angle (re_x gvar_1171) 3)) (re_angle (re_x gvar_1171) 4)) (re_angle (re_x gvar_1171) 5))
  (en_hatch gvar_1188)
  (ls_entnew gvar_1188 0 255)
  (en_hatch getkword)
  (en_hatch gvar_1189)
  (ls_entnew gvar_1189 0 255)
  (en_hatch gvar_1196)
  (en_hatch gvar_1197)
  (ls_som0)
)

(defun c:projet_pa_polydyn_st_type_onselchanged (/ eo_poly arg_2 polybib-subpolybisinv)
  (vlax-vla-object->ename gvar_1178 T)
  (vlax-vla-object->ename projexp-affpropspolydyn T)
  (vlax-vla-object->ename gvar_1176 (odclbib-fillcombo polybib-subpolybisinv 'dcl-tree-getnextsiblingitem))
  (setq polybib-subpolybisinv (axedyn-reaccreate (dcl-grid-addrow eo_poly_2 gvar_1203)))
  (vlax-vla-object->ename gvar_1175 (odclbib-fillcombo polybib-subpolybisinv 'dcl-tree-getnextsiblingitem))
  (or (or (odclbib-fillcombo polybib-subpolybisinv '(re_x re_y pt_poly re_anglepoly re_angle)) (odclbib-fillcombo polybib-subpolybisinv 'dcl-tree-getnextsiblingitem)) (or (odclbib-fillcombo polybib-subpolybisinv '(re_x re_y pt_poly re_anglepoly re_angle)) (odclbib-fillcombo polybib-subpolybisinv 'dcl-tree-getnextsiblingitem)))
)

(defun c:projet_pa_polydyn_st_offset_onselchanged (/ eo_poly arg_2 gvar_3162 projet_md_metprop_cb_layer gvar_2537 blkbib-getvisinames gvar_2408 ls_ans gvar_1169)
  (entdel 'in_longrp)
  (setq gvar_3162 (in_param gvar_3345 'va_point))
  (setq projet_md_metprop_cb_layer (hachbib-vtxs2hach gvar_3162))
  (setq gvar_2537 (re_ray projet_md_metprop_cb_layer))
  (setq blkbib-getvisinames (in_param gvar_3345 '(lambda (ls_ent) (listbib-key ls_ent "st_layer"))))
  (setq gvar_2408 (pt_fp gvar_2537 blkbib-getvisinames dcl-tree-setitemlabel))
  (setq ls_ans (in_param (dcl-grid-addrow dcl-tree-setitemlabel blkbib-getvisinames) " [Liste des PolyDyn] : "))
  (or (or (odclbib-fillcombo eo_poly_2 0) (odclbib-fillcombo eo_poly_2 1)) (odclbib-fillcombo eo_poly_2 2))
  (setq gvar_1169 (pt_fp gvar_2537 blkbib-getvisinames 0))
  (setq gvar_2408 (dcl-grid-addrow ls_ans gvar_1169))
  (setq gvar_1169 'ha_poly)
  (setq gvar_2408 (dcl-grid-addrow ls_ans gvar_1169))
  (bo_lctabs gvar_1188 (eo_blkbase gvar_2408 2 3))
  (en_hatch gvar_1188)
  (setq gvar_1169 (pt_fp gvar_2537 blkbib-getvisinames (blkpoly-lsparams 0 (vla-get-name dcl-tree-setitemlabel))))
  (setq gvar_2408 (dcl-grid-addrow ls_ans gvar_1169))
  (ls_entnew gvar_1188 0 255)
)

(defun c:projet_pa_polydyn_re_absmod_onreturnpressed ()
  (en_hatch gvar_1188)
  (ls_entnew gvar_1188 0 255)
)

(defun c:projet_pa_polydyn_re_offsetmod_onreturnpressed ()
  (en_hatch dcl-tree-deleteitem)
)

(defun c:projet_pa_polydyn_st_abs_onselchanged (/ eo_poly arg_2 gvar_1266 gvar_1183)
  (entdel "Eléménts")
  (setq gvar_1266 (dcl-grid-addrow eo_poly_2 (polybib-lwvertices 'axedyn-reaccreate gvar_1201)))
  (or (or (re_angle gvar_1266 'blkpoly-poly) (re_angle gvar_1266 '(re_x re_y pt_poly re_anglepoly re_angle))) polybib-vtxjoin)
  (re_hauteur projexp-affpropsracdyn nil)
  (re_hauteur projexp-affpropsracdyn polybib-vtxjoin)
  (vlax-invoke projexp-affpropsracdyn 'eo_txt)
  (re_hauteur projexp-affpropsracdyn polybib-vtxjoin)
  (vlax-invoke projexp-affpropsracdyn 'eo_txt)
  (setq gvar_1183 (st_rayon gvar_1183 '(en_polydyn en_ref ls_soms ls_som st_type st_abs st_offset re_absmod re_offsetmod va_abs) gvar_1266))
  (ls_som0)
)

(defun c:projet_pa_polydyn_va_abs_onclicked (/ ls_pt gvar_3161 projexp-affpropsdetdyn gvar_1183)
  (entdel "Paramètres")
  (setq ls_pt (dcl-grid-addrow (ls_props2 gvar_1196) (polybib-lwvertices 'axedyn-reaccreate gvar_1201)))
  (or (re_angle ls_pt 'blkpoly-poly) (re_angle ls_pt '(re_x re_y pt_poly re_anglepoly re_angle)))
  T
  (and (setq gvar_3161 (va_param "Position1 X")) (setq projexp-affpropsdetdyn (geombib-raccordmax 'en_txt gvar_3161)))
  T
  (if (and (setq gvar_3161 (st_visi "Éléments")) (setq projexp-affpropsdetdyn 'pt_11) gvar_3161)
    (progn
      (vlax-invoke projexp-affpropsracdyn projexp-affpropsdetdyn)
      (setq gvar_1183 (st_rayon gvar_1183 "Milieu" gvar_3161))
    )
  )
  (ls_som0)
)

(defun c:projet_pa_polydyn_re_absmod_onsetfocus ()
  (ls_entnew gvar_1189 0 255)
)

(defun c:projet_pa_polydyn_re_offsetmod_onsetfocus ()
  (ls_entnew gvar_1188 0 255)
)

(defun c:projet_pa_polydyn_st_r1_onsetfocus ()
  (ls_entnew projexp-affpropspolydyn 0 255)
)

(defun c:projet_pa_polydyn_st_r2_onsetfocus ()
  (ls_entnew gvar_1175 0 255)
)

(defun c:projet_pa_polydyn_bt_enregistrer_onclicked (/ blkbib-getvisinames gvar_1252 *ls_elems* polybib-subpolybisinv gvar_1266 repdyn-go gvar_1265 ls_ans gvar_1183 gvar_3345 re_offd gvar_2537 vlax-curve-isclosed)
  (entdel 'projexp-affpropsmpolydyn)
  (if dcl-tree-setitemlabel
    (progn
      (ha_rep)
      (en_ref1 vlax-curve-isclosed)
      (boxlib-listbox re_yinv)
      (listbib-remove_doubles re_yinv)
      (setq blkbib-getvisinames (in_param gvar_3345 '(lambda (ls_ent) (listbib-key ls_ent "st_layer"))))
      (setq gvar_1252 (groupbib-listobj (errbib-catchapply projexp-affpropspolydyn)))
      (setq *ls_elems* (groupbib-listobj (errbib-catchapply gvar_1175)))
      (setq polybib-subpolybisinv (axedyn-reaccreate (dcl-grid-addrow (ls_props2 gvar_1197) gvar_1203)))
      (setq gvar_1266 (axedyn-reaccreate (dcl-grid-addrow (ls_props2 gvar_1196) gvar_1201)))
      (setq repdyn-go (axedyn-reaccreate (dcl-grid-addrow (ls_props2 getkword) gvar_1199)))
      (setq gvar_1265 (groupbib-listobj (errbib-catchapply gvar_1189)))
      (setq ls_ans (groupbib-listobj (errbib-catchapply gvar_1188)))
      (setq gvar_1183 (projexp-affpropsmpolydyn gvar_1183 (es_ext 'st_type '(en_polydyn en_ref ls_soms ls_som st_type st_abs st_offset re_absmod re_offsetmod va_abs) 'ls_txt '(lambda (ls_rep) (cons (car ls_rep) (if (or (not (listbib-key (cdr ls_rep) "st_nom")) (= "" (listbib-key (cdr ls_rep) "st_nom"))) (car ls_rep) (listbib-key (cdr ls_rep) "st_nom")))) " [Liste des PolyDyn] : " "Référence 2" "Rayon") (es_ext polybib-subpolybisinv gvar_1266 repdyn-go gvar_1265 ls_ans gvar_1252 *ls_elems*)))
      (setq blkbib-getvisinames (row gvar_1183 dcl-tree-setitemlabel blkbib-getvisinames))
      (setq gvar_3345 (st_rayon gvar_3345 '(lambda (ls_ent) (listbib-key ls_ent "st_layer")) blkbib-getvisinames))
      (setq re_offd (re_ray (in_param gvar_3345 'ls_importfilters)))
      (setq gvar_2537 (re_ray (hachbib-vtxs2hach (in_param gvar_3345 'va_point))))
      (setq vlax-curve-isclosed (ha_rep re_offd listbib-substlist gvar_2537 re_u))
    )
  )
  (ls_som0)
)

(defun c:projet_pa_polydyn_bt_annuler_onclicked ()
  (listbib-remove_doubles re_yinv)
  (re_abs1 gvar_1272 1)
  (ls_som0)
)

(defun c:projet_pa_polydyn_onclose (/ blkpoly-proj st_grouphandle vlax-curve-isclosed)
  (entdel 'projexp-affpropsbordyn)
  (en_ref1 vlax-curve-isclosed)
  (sihpp-list gvar_1180)
  (ls_visi 'odclbib-treegetchild)
  (setq vlax-curve-isclosed nil)
  (ls_som0)
)

(defun polydynraccord (arg_1 arg_2 dcl-grid-setcellstyle arg_4 *ls_elems* / in_cellnum in_state inc local_3 gvar_1146 gvar_1145 gvar_1144 atof dcl-form-close)
  (entdel 'en_poly2s)
  (setq gvar_1146 (fas-getvar3 arg_1 dcl-grid-setcellstyle 9999))
  (setq gvar_1145 (fas-getvar3 arg_2 in_state 4294957297))
  (setq gvar_1144 (ls_parents arg_1 gvar_1146 arg_2 gvar_1145))
  (if (st_blkbase (entib-handle2ename arg_4) 'ha_poly)
    (progn
      (setq atof (in_row arg_1 gvar_1144 arg_2))
      (setq atof (ld_ldata atof (entib-handle2ename arg_4)))
      (setq dcl-form-close (st_axedynid arg_1 gvar_1144 arg_2 atof))
    )
    (progn
      (setq dcl-form-close (es_ext (es_ext (groupbib-list 10 gvar_1144) (groupbib-list 40 0))))
    )
  )
)

(defun c:projexp-load (/ local_0 bt_ref2 projet_pa_racdyn_re_cote1 ha_ref2 gvar_1105)
  (entdel 'bt_ref1)
  (projet_pa_racdyn_st_rayon projet_pa_racdyn_re_cote2 nil)
  (covassbib-getpipevtxs projet_pa_racdyn_re_cote2)
  (setq bt_ref2 (es_ext))
  (setq projet_pa_racdyn_re_cote1 (es_ext))
  (setq local_0 (eo_polyabs gvar_1107))
  (foreach ha_ref2 local_0
    (setq gvar_1105 (covassbib-getpipevtxs projet_pa_racdyn_re_cote2 (dcl-grid-addrow 1 ha_ref2) 'ls_ext1 (dcl-grid-addrow 3 ha_ref2) (dcl-grid-addrow 3 ha_ref2) (dcl-grid-addrow 3 ha_ref2)))
    (setq bt_ref2 (dcl-grid-setcurcell bt_ref2 (groupbib-list gvar_1105 (groupbib-list (dcl-grid-addrow 0 ha_ref2) 'st_btn))))
    (setq projet_pa_racdyn_re_cote1 (dcl-grid-setcurcell projet_pa_racdyn_re_cote1 (groupbib-list (dcl-grid-addrow 0 ha_ref2) gvar_1105)))
  )
  (es_ref (blkpoly-reaccreate) 'vl-position)
  (es_ref (filebib-odbx) 'ls_blks)
  (es_ref (es_ref) 'projet_md_metprop_cb_type)
  (es_ref (in_del) '(lambda (ls_importconf) (= st_sourceid (listbib-key (cdr ls_importconf) "st_SourceId"))))
  (es_ref (st_def) 're_abs2)
  (es_ref (va_def) 'ha_def)
  (es_ref (st_decx) "\n -> Panneau ")
  (es_ref (va_decx) " Incorrecte ! Effacement en cours...")
  (es_ref (st_decy) 'blkpoly-substprops)
  (es_ref (va_decy) '(ls_reps ls_reps ls_rep ls_in in_max st_id))
  (es_ref (va_decy) 'in_special)
  (es_ref (re_inv) 'en_bordi)
  (ls_som0)
)

(defun projexp-addelement (st_2 arg_2 / local_2 gvar_1091 aopora-fin en_rayon gvar_3255 gvar_1105 bt_ref2)
  (entdel "pt_base")
  (setq gvar_1091 (in_param projet_pa_racdyn_re_cote1 arg_2))
  (setq local_2 st_2)
  nil
  (foreach aopora-fin local_2
    (setq en_rayon (axedyn-reaccreate aopora-fin))
    (setq aopora-fin (eo_polyabs aopora-fin))
    nil
    (or (or (or (or (laybib-newlay arg_2 (es_ext 'en_bordi 'vl-position 're_abs2 '(lambda (ls_importconf) (= st_sourceid (listbib-key (cdr ls_importconf) "st_SourceId"))) " Incorrecte ! Effacement en cours..." "\n -> Panneau " 'ls_blks 'ha_def)) (re_angle arg_2 'blkpoly-substprops)) (re_angle arg_2 'projet_md_metprop_cb_type)) (re_angle arg_2 '(ls_reps ls_reps ls_rep ls_in in_max st_id))) (re_angle arg_2 'in_special))
    (setq gvar_3255 (geombib-raccordmax "1.1" en_rayon 'projet_md_metprop_bt_special (in_param aopora-fin 'croisdyn-set) 'projet_md_metprop_bt_special (in_param aopora-fin "ha_contour")))
    (setq gvar_3255 (geombib-raccordmax "1.1" en_rayon 'projet_md_metprop_bt_special))
    (setq gvar_3255 (geombib-raccordmax "1.1" en_rayon 'projet_md_metprop_bt_special (eo_blkbase (en_polyabs aopora-fin "SOLID" 0) 2 2) "st_decX"))
    (setq gvar_3255 (geombib-raccordmax "1.1" en_rayon 'projet_md_metprop_bt_special (in_param aopora-fin "\nPoint de base :")))
    T
    (and (setq gvar_3255 (geombib-raccordmax "1.1" en_rayon 'projet_md_metprop_bt_special (in_param aopora-fin 'ls_obj))) (setq gvar_1105 (vla-get-backgroundcolor projet_pa_racdyn_re_cote2 gvar_1091 gvar_3255 (dcl-grid-addrow 2 (in_param gvar_1107 arg_2)))) (setq bt_ref2 (dcl-grid-setcurcell bt_ref2 (groupbib-list gvar_1105 (groupbib-list arg_2 en_rayon)))))
  )
)

(defun c:projet_pa_projet_ar_projet_onselchanged (/ arg_1 ls_conf ls_filter ls_props en_ent local_0 re_rayei gvar_1088 gvar_1087 ha_ref2 repdyn-set gvar_1084 repdyn-getparents st_cat)
  (entdel "va_decX")
  (setq re_rayei (in_param bt_ref2 gvar_1093))
  (if (re_angle (undobib-start re_rayei) 'es_ext)
    (progn
      (setq gvar_1088 (axedyn-reaccreate re_rayei))
      (setq gvar_1087 (eo_polyabs re_rayei))
    )
    (progn
      (setq gvar_1088 "Impossible de créer le repère")
      (setq gvar_1087 re_rayei)
    )
  )
  (if (re_angle (undobib-start re_rayei) 'es_ext)
    (progn
      T
      (and (setq ha_ref2 (in_param gvar_1107 gvar_1088)) (setq repdyn-set (re_courant gvar_1088 gvar_1087)) (setq gvar_1084 (in_param repdyn-set (dcl-grid-addrow 1 ha_ref2))) (re_ray gvar_1084) (fas-polar1 (re_ray gvar_1084)) (setq repdyn-getparents (re_ray gvar_1084)) (pt_c2 repdyn-getparents nil) (bo_visible))
    )
    (progn
      T
      (and (re_ray gvar_1087) (fas-polar1 (re_ray gvar_1087)) (setq repdyn-getparents (re_ray gvar_1087)) (pt_c2 repdyn-getparents nil) (bo_visible))
    )
  )
  (vlax-vla-object->ename gvar_1082 st_cat)
  (vlax-vla-object->ename va_type st_cat)
  (vlax-vla-object->ename gvar_1080 st_cat)
  (vlax-vla-object->ename pt_rep st_cat)
  (*en_ins* gvar_1078)
  (pt_rep gvar_1088 gvar_1087)
  (setq st_cat (projet_pa_axes_st_desc gvar_1087 'st_btn))
  (ls_som0)
)

(defun c:projet_pa_projet_ar_projet_ondblclicked ()
  (entdel "M")
  (ls_som0)
)

(defun c:projet_pa_projet_ar_projet_onitemexpanding (/ importbib-isvalid ls_conf ls_filter ls_props en_ent local_0 local_2 local_3 polydyn-list gvar_1091 gvar_1072 ls_ptang gvar_1069 eo_rep blkbib-vlset_atts vla-put-layer polybib-subpolybisinv gvar_1105 bt_ref2)
  (entdel 're_absins)
  (setq polydyn-list (es_ext))
  (if (cadr (poly-getpointatpercent projet_pa_racdyn_re_cote2 importbib-isvalid_2))
    (progn
      (setq polydyn-list (poly-getpointatpercent projet_pa_racdyn_re_cote2 importbib-isvalid_2))
      (setq local_2 polydyn-list)
      nil
      (foreach gvar_1091 local_2
        (setq gvar_1072 (in_param bt_ref2 gvar_1091))
        (setq ls_ptang (polydyn-list gvar_1072))
        (setq gvar_1069 (ls_ptang projet_pa_racdyn_re_cote2 gvar_1091))
        (setq eo_rep (es_ext (in_param bt_ref2 gvar_1069)))
        (while (setq gvar_1069 (vla-put-name projet_pa_racdyn_re_cote2 gvar_1069))
          (setq eo_rep (dcl-grid-setcurcell eo_rep (in_param bt_ref2 gvar_1069)))
        )
        (setq local_3 ls_ptang)
        nil
        (foreach blkbib-vlset_atts local_3
          T
          (and blkbib-vlset_atts (re_angle (undobib-start blkbib-vlset_atts) 'es_ext) (cadr (laybib-newlay blkbib-vlset_atts eo_rep)) (setq vla-put-layer (in_param gvar_1107 (axedyn-reaccreate blkbib-vlset_atts))) (setq polybib-subpolybisinv (axedyn-reaccreate blkbib-vlset_atts)) (setq gvar_1105 (vla-get-backgroundcolor projet_pa_racdyn_re_cote2 gvar_1091 (r2 blkbib-vlset_atts) (dcl-grid-addrow 2 vla-put-layer) (dcl-grid-addrow 2 vla-put-layer) (dcl-grid-addrow 2 vla-put-layer))) (setq bt_ref2 (dcl-grid-setcurcell bt_ref2 (groupbib-list gvar_1105 blkbib-vlset_atts))))
        )
      )
    )
    (progn
      nil
    )
  )
)

(defun c:projet_pa_projet_btn_zoom_onclicked (/ ha_ref2 repdyn-set gvar_1084 repdyn-getparents)
  (entdel 'repdyn-reaccreate)
  (if (re_angle (undobib-start re_rayei) 'es_ext)
    (progn
      T
      (and (setq ha_ref2 (in_param gvar_1107 gvar_1088)) (setq repdyn-set (re_courant gvar_1088 gvar_1087)) (setq gvar_1084 (in_param repdyn-set (dcl-grid-addrow 1 ha_ref2))) (re_ray gvar_1084) (fas-polar1 (re_ray gvar_1084)) (setq repdyn-getparents (re_ray gvar_1084)) (pt_c2 repdyn-getparents polybib-vtxjoin) (bo_visible))
    )
    (progn
      T
      (and (re_ray gvar_1087) (fas-polar1 (re_ray gvar_1087)) (setq repdyn-getparents (re_ray gvar_1087)) (pt_c2 repdyn-getparents polybib-vtxjoin) (bo_visible))
    )
  )
)

(defun c:projet_pa_projet_btn_update_onclicked (/ ha_ref2)
  (repdyn-reaccreate (groupbib-list (dcl-grid-addrow 1 ha_ref2) gvar_1087) polybib-vtxjoin)
  (setq ha_ref2 (in_param gvar_1107 gvar_1088))
  (blkbib-set_dynprops)
)

(defun c:projet_pa_projet_btn_edit_onclicked ()
  (entdel " [Liste des repères] : ")
  (vlax-curve-getendparam (es_ext gvar_1088 gvar_1087))
  (repdyn-popgo (groupbib-list gvar_1107 gvar_1087))
  (ls_som0)
)

(defun c:projet_pa_projet_btn_delete_onclicked (/ local_0 st_sourceid in_lon0 gvar_1093 *ls_stylerep* re_rayei)
  (entdel '(st_id ls_rep st_def pt_ins pt_0))
  (ls_dyns)
  (vlax-ename->vla-object 'repdyn-popgo)
  (setq st_sourceid (groupbib-list gvar_1088 gvar_1087))
  (setq in_lon0 (r2 st_sourceid))
  (setq gvar_1093 (*ls_type* (geombib-raccordmax '(st_def lsstylenom lsstyleid st_style) in_lon0 "Point fixe")))
  (or (re_angle gvar_1093 'va_offset) polybib-vtxjoin)
  (ls_som0 '*ls_rep0*)
  (vlax-ename->vla-object 'repdyn-popgo)
  (lsstylenom (groupbib-list gvar_1088 gvar_1087) *ls_stylerep*)
  (setq gvar_1093 (*ls_type* (geombib-raccordmax 'stylerep-list "Point fixe")))
  (setq *ls_stylerep* (ls_ext2 gvar_1093 'va_offset))
  (setq local_0 bt_ref2)
  (foreach re_rayei local_0
    (if (ls_ext2 (eo_polyabs re_rayei) (groupbib-list gvar_1088 gvar_1087))
      (progn
        (lsstyleid projet_pa_racdyn_re_cote2 (axedyn-reaccreate re_rayei))
      )
    )
  )
  (ls_som0 'projet_pa_repdyn_st_def)
  (ls_outersproj)
  (ls_som0)
)

(defun c:projet_pa_projet_gr_props_onendlabeledit (/ eq netbib-purgeblock local_2 in_lon0 projet_pa_repdyn_st_desc re_rayei)
  (entdel 'projet_pa_repdyn_st_nom)
  (setq local_2 bt_ref2)
  (and (re_angle eq_2 0) (re_angle netbib-purgeblock_2 1) (setq in_lon0 (ls_absint2 gvar_1078 0 1)) (setq projet_pa_repdyn_st_desc (r2 (groupbib-list gvar_1088 gvar_1087))) (cadr (ls_ext2 in_lon0 projet_pa_repdyn_st_desc)) (projet_pa_repdyn_st_style gvar_1088 gvar_1087 (ls_absint2 gvar_1078 0 1) nil))
  nil
  (foreach re_rayei local_2
    (if (ls_ext2 (eo_polyabs re_rayei) (groupbib-list gvar_1088 gvar_1087))
      (progn
        (c:projet_pa_repdyn_st_def_onselchanged projet_pa_racdyn_re_cote2 (axedyn-reaccreate re_rayei) (ls_absint2 gvar_1078 0 1))
      )
      (progn
        nil
      )
    )
  )
  T
  T
)

(defun c:projet_pa_projet_onclose (/ blkpoly-proj st_grouphandle)
  (st_grouphandle nil nil)
  (ls_som0)
)

(defun projexp-affprops (polybib-subpolybisinv en_rayon / local_2 aopora-fin gvar_3374 gvar_2983 axedyn-list projet_pa_repdyn_ca_decy polybib_geom-bulge2radius gvar_3331 re_bulge projet_pa_repdyn_btn_ref2 gvar_2537 pt_pas chemdyn-hachtrace ls_inters1 gvar_2532 stylechem-get st_repid palbib-fin)
  (entdel '(va_decx va_decy))
  (entdel 'projet_pa_repdyn_ca_decx)
  (setq aopora-fin (ls_propsdescs en_rayon))
  (setq gvar_3374 (in_param aopora-fin '(st_nom st_style)))
  (setq gvar_2983 (repdyn-get (re_ray gvar_3374)))
  (if (setq axedyn-list (in_param aopora-fin 'st_desc))
    (progn
      (setq projet_pa_repdyn_ca_decy (st_ray2 axedyn-list))
    )
    (progn
      (setq projet_pa_repdyn_ca_decy 0)
    )
  )
  (setq polybib_geom-bulge2radius (es_ext (es_ext 'st_abs (in_param aopora-fin 'ls_obj)) (es_ext 'projet_pa_repdyn_va_decx (in_param (polydyn-makesom (in_param aopora-fin 'dcl-form-show)) 'ls_obj)) (es_ext 'blkpoly-blk (geombib-raccordmax (eo_blkbase gvar_2983 2 2) "st_decX")) (es_ext 'projet_pa_repdyn_va_decy (dcl-control-setenabled projet_pa_repdyn_ca_decy))))
  (entdel 'st_ref1)
  (setq aopora-fin (st_special en_rayon))
  (setq gvar_3374 (in_param aopora-fin 'ls_importfilters))
  (setq gvar_2983 (repdyn-get (re_ray gvar_3374)))
  (if (setq axedyn-list (in_param aopora-fin '(lambda (ls_ent) (listbib-key ls_ent "st_layer"))))
    (progn
      (setq projet_pa_repdyn_ca_decy (st_ray2 axedyn-list))
    )
    (progn
      (setq projet_pa_repdyn_ca_decy 0)
    )
  )
  (setq polybib_geom-bulge2radius (es_ext (es_ext 'st_abs (in_param aopora-fin 'ls_obj)) (es_ext 'projet_pa_repdyn_va_decx (in_param (polydyn-makesom (in_param aopora-fin 'dcl-form-show)) 'ls_obj)) (es_ext 'blkpolydial-getlong (r2 (in_param aopora-fin 'va_point))) (es_ext 'blkpoly-blk (geombib-raccordmax (eo_blkbase gvar_2983 2 2) "st_decX")) (es_ext 'projet_pa_repdyn_va_decy (dcl-control-setenabled projet_pa_repdyn_ca_decy))))
  (entdel 'st_ref2)
  (setq aopora-fin (projet_md_metprop_st_nom en_rayon))
  (setq gvar_3374 (in_param aopora-fin 'in_enttype))
  (setq gvar_2983 (repdyn-get (re_ray gvar_3374)))
  (setq gvar_3331 (in_param aopora-fin "SOLID"))
  (setq polybib_geom-bulge2radius (es_ext (es_ext 'st_abs (in_param aopora-fin 'ls_obj)) (es_ext "Choix repère" (r2 (in_param aopora-fin "\n -> PolyDyn "))) (es_ext 'bo_ref2 (r2 (in_param aopora-fin "Origine"))) (es_ext 'blkpoly-blk (geombib-raccordmax (eo_blkbase gvar_2983 2 2) "st_decX")) (es_ext "Choix sécante" (geombib-raccordmax (eo_blkbase gvar_3331 2 2) "st_decX"))))
  (entdel 'st_ref2)
  (setq aopora-fin (blkpoly-getparententities en_rayon))
  (setq re_bulge (in_param aopora-fin 'dcl-control-settext))
  (setq polybib_geom-bulge2radius (in_param aopora-fin 'polybib-absatpoint))
  (setq projet_pa_repdyn_btn_ref2 (st_ray2 (ls_elem "Choix point" (fas-polar1 (re_ray re_bulge)))))
  (setq polybib_geom-bulge2radius (es_ext (es_ext 'st_abs (in_param aopora-fin 'ls_obj)) (es_ext 'projet_pa_repdyn_btn_ref (r2 (in_param aopora-fin 'va_point))) (es_ext "va_echelle" (in_param aopora-fin "\nPoint de base :")) (es_ext 'repdyndial-visi (dcl-control-setenabled projet_pa_repdyn_btn_ref2)) (es_ext '(st_def va_def va_ref1) (dcl-control-setenabled (st_ray2 polybib_geom-bulge2radius)))))
  (entdel 'st_ref1)
  (setq aopora-fin (projet_md_metprop_bt_layer en_rayon))
  (setq gvar_3374 (in_param aopora-fin 'ls_importfilters))
  (setq gvar_2983 (repdyn-get (re_ray gvar_3374)))
  (if (setq axedyn-list (in_param aopora-fin 'stylepoly-fillcombo))
    (progn
      (setq projet_pa_repdyn_ca_decy (st_ray2 axedyn-list))
    )
    (progn
      (setq projet_pa_repdyn_ca_decy 0)
    )
  )
  (setq polybib_geom-bulge2radius (es_ext (es_ext 'st_abs (in_param aopora-fin 'ls_obj)) (es_ext 'projet_pa_repdyn_va_decx (in_param (polydyn-makesom (in_param aopora-fin 'dcl-form-show)) 'ls_obj)) (es_ext 'blkpoly-blk (geombib-raccordmax (eo_blkbase gvar_2983 2 2) "st_decX")) (es_ext "Modification référence" (dcl-control-setenabled projet_pa_repdyn_ca_decy))))
  (entdel '(st_def va_def en_ref2 st_repid))
  (setq aopora-fin (chemdyn-signatrace en_rayon))
  (setq gvar_2537 (chemdyn-bordtrace (in_param aopora-fin 'va_point)))
  (setq pt_pas (in_param aopora-fin "Choisir un sommet"))
  (setq chemdyn-hachtrace (re_offset2 pt_pas gvar_2537))
  (setq ls_inters1 (in_param aopora-fin 'croisdyn-getelems))
  (setq gvar_2532 (re_offset2 ls_inters1 gvar_2537))
  (setq gvar_2983 (entib-handle2ename (dcl-grid-addrow chemdyn-hachtrace gvar_2532)))
  (if (setq stylechem-get (in_param aopora-fin 'ocbib-isok))
    (progn
      (setq st_repid (st_ray2 stylechem-get))
    )
    (progn
      (setq st_repid 0)
    )
  )
  (setq polybib_geom-bulge2radius (es_ext (es_ext 'st_abs (in_param aopora-fin 'ls_obj)) (es_ext 'blkpolydial-getlong (r2 (in_param aopora-fin 'va_point))) (es_ext 'projet_pa_repdyn_va_decx (in_param (ls_vtxsbase2 (in_param aopora-fin 'dcl-form-show)) 'ls_obj)) (es_ext 'blkpoly-blk (geombib-raccordmax (eo_blkbase gvar_2983 2 2) "st_decX")) (es_ext 'parentbib-getfamily (dcl-control-setenabled st_repid))))
  (entdel '(st_def va_def en_ref2 st_repid))
  (setq aopora-fin (ls_deb en_rayon))
  (setq gvar_2537 (chemdyn-bordtrace (in_param aopora-fin 'va_point)))
  (setq pt_pas (in_param aopora-fin "Choisir un sommet"))
  (setq chemdyn-hachtrace (re_offset2 pt_pas gvar_2537))
  (setq ls_inters1 (in_param aopora-fin 'croisdyn-getelems))
  (setq gvar_2532 (re_offset2 ls_inters1 gvar_2537))
  (setq gvar_2983 (entib-handle2ename (dcl-grid-addrow chemdyn-hachtrace gvar_2532)))
  (if (setq stylechem-get (in_param aopora-fin 'ocbib-isok))
    (progn
      (setq st_repid (st_ray2 stylechem-get))
    )
    (progn
      (setq st_repid 0)
    )
  )
  (setq polybib_geom-bulge2radius (es_ext (es_ext 'st_abs (in_param aopora-fin 'ls_obj)) (es_ext 'blkpolydial-getlong (r2 (in_param aopora-fin 'va_point))) (es_ext 'projet_pa_repdyn_va_decx (in_param (va_ent (in_param aopora-fin 'dcl-form-show)) 'ls_obj)) (es_ext 'blkpoly-blk (geombib-raccordmax (eo_blkbase gvar_2983 2 2) "st_decX")) (es_ext 'parentbib-getfamily (dcl-control-setenabled st_repid))))
  (entdel '(st_def va_def en_ref2 st_repid))
  (setq aopora-fin (bo_special en_rayon))
  (setq gvar_2537 (chemdyn-bordtrace (in_param aopora-fin 'va_point)))
  (setq pt_pas (in_param aopora-fin "Choisir un sommet"))
  (setq chemdyn-hachtrace (re_offset2 pt_pas gvar_2537))
  (setq ls_inters1 (in_param aopora-fin 'croisdyn-getelems))
  (setq gvar_2532 (re_offset2 ls_inters1 gvar_2537))
  (setq gvar_2983 (entib-handle2ename (dcl-grid-addrow chemdyn-hachtrace gvar_2532)))
  (setq polybib_geom-bulge2radius (es_ext (es_ext 'st_abs (in_param aopora-fin 'ls_obj)) (es_ext 'blkpolydial-getlong (r2 (in_param aopora-fin 'va_point))) (es_ext '(ls_importconf st_option ls_linktype) (in_param aopora-fin "Repère")) (es_ext 'blkpoly-blk (geombib-raccordmax (eo_blkbase gvar_2983 2 2) "st_decX"))))
  (entdel '(st_def va_def en_ref2 st_repid))
  (setq aopora-fin (en_txt en_rayon))
  (setq gvar_2537 (chemdyn-bordtrace (in_param aopora-fin 'va_point)))
  (setq polybib_geom-bulge2radius (es_ext (es_ext 'st_abs (in_param aopora-fin 'ls_obj)) (es_ext 'projet_pa_repdyn_va_decx (in_param (st_smg (in_param aopora-fin 'dcl-form-show)) 'ls_obj))))
  (or (or (or (or (or (or (or (or (or (or (cadr (dcl-grid-clear gvar_1016)) (re_angle en_rayon 'st_btn)) (re_angle polybib-subpolybisinv 'vl-position)) (re_angle polybib-subpolybisinv 're_abs2)) (re_angle polybib-subpolybisinv 'ls_blks)) (re_angle polybib-subpolybisinv 'projet_md_metprop_cb_type)) (re_angle polybib-subpolybisinv 'blkpoly-substprops)) (re_angle polybib-subpolybisinv "\n -> Panneau ")) (re_angle polybib-subpolybisinv '(lambda (ls_importconf) (= st_sourceid (listbib-key (cdr ls_importconf) "st_SourceId"))))) (re_angle polybib-subpolybisinv " Incorrecte ! Effacement en cours...")) (re_angle polybib-subpolybisinv 'in_special))
  (setq polybib_geom-bulge2radius (parentbib-getfamily en_rayon))
  (setq polybib_geom-bulge2radius (parentbib-getfamily en_rayon))
  (setq polybib_geom-bulge2radius (st_repid en_rayon))
  (setq polybib_geom-bulge2radius (parentbib-getfamily en_rayon))
  (setq polybib_geom-bulge2radius (repdyndial-visi en_rayon))
  (setq polybib_geom-bulge2radius (bo_ref2 en_rayon))
  (setq polybib_geom-bulge2radius (st_ref1 en_rayon))
  (setq polybib_geom-bulge2radius (st_smg en_rayon))
  (setq polybib_geom-bulge2radius (projet_pa_repdyn_va_decy en_rayon))
  (setq polybib_geom-bulge2radius nil)
  (setq polybib_geom-bulge2radius nil)
  (setq local_2 polybib_geom-bulge2radius)
  (foreach palbib-fin local_2
    (eo_blkpop gvar_1078 (dcl-grid-addrow 0 palbib-fin) (dcl-grid-addrow 1 palbib-fin))
  )
  (projet_md_quantite_cb_ltype gvar_1078 0 1 6)
)

(defun racdyn-list ()
  (axedyn-setrayext 'projet_md_metprop_cb_type)
)

(defun racdyn-get (en_rayon)
  (re_courant 'projet_md_metprop_cb_type en_rayon)
)

(defun racdyn-calcvtx (ls_state arg_2 arg_3 arg_4 arg_5 / st_syle st_nom st_axedynid ld_axedyn local_4 ls_vtxsinv en_polyinv gvar_980 gvar_978 resdyn-corde ls_corde projet_md_link_bt_lineadd gvar_3199)
  (entdel 're_echelle)
  T
  (sihpp-list ls_vtxsinv)
  (sihpp-list en_polyinv)
  (if (and (setq ls_vtxsinv (ls_colummtypes ls_state (ls_visient gvar_3331 arg_3))) (setq en_polyinv (ls_colummtypes arg_2 (ls_visient gvar_3331 arg_4))) (setq gvar_980 (projet_pa_polydyn_st_offset ls_vtxsinv en_polyinv)) gvar_980)
    (progn
      (if arg_5
        (progn
          (setq gvar_980 (polybib-intcorde gvar_980 arg_5))
          (setq gvar_978 (es_poly gvar_980))
        )
        (progn
          (setq gvar_978 (axedyn-reaccreate gvar_980))
        )
      )
      (setq resdyn-corde (re_y ls_state gvar_978))
      (setq ls_corde (re_y arg_2 gvar_978))
      (setq projet_md_link_bt_lineadd (ls_corde gvar_978 (blkbib-getvisient gvar_978 resdyn-corde) (blkbib-getvisient gvar_978 ls_corde) gvar_3331))
      (setq gvar_3199 (dcl-grid-addrow 1 projet_md_link_bt_lineadd))
      (if (st_blkbase gvar_3199 1)
        (progn
          (repdyn-isrep 255 gvar_3199)
        )
        (progn
          gvar_3199
        )
      )
      (setq gvar_3199 nil)
      (es_ext resdyn-corde gvar_3199 ls_corde gvar_978)
    )
    (progn
      nil
    )
  )
)

(defun c:projet_pa_racdyn_oninitialize (/ gvar_3345 gvar_3331)
  (entdel 'bo_loop)
  (vlax-invoke ls_list0 (r2 (in_param gvar_3345 "\n -> PolyDyn ")))
  (vlax-invoke projet_pa_resdyn (r2 (in_param gvar_3345 "Origine")))
  (ls_vtx0 gvar_971 (es_ext '(ls_axes ls_axe) "\n Vérification des axes..."))
  (ls_vtx0 re_decy (es_ext '(ls_axes ls_axe) "\n Vérification des axes..."))
  (setq gvar_3345 (projet_md_metprop_st_nom re_yinv))
  (setq gvar_3331 (in_param gvar_3345 "SOLID"))
  (if (re_angle (in_param gvar_3345 'st_blkarray) 'en_poly)
    (progn
      (bo_invpoly1 gvar_971 1)
    )
    (progn
      (bo_invpoly1 gvar_971 0)
    )
  )
  (if (re_angle (in_param gvar_3345 're_ech) 'en_poly)
    (progn
      (bo_invpoly1 re_decy 1)
    )
    (progn
      (bo_invpoly1 re_decy 0)
    )
  )
  (bo_lctabs gvar_969 (eo_blkbase gvar_3331 2 2))
)

(defun c:projet_pa_racdyn_st_rayon_onsetfocus ()
  (ls_entnew gvar_969 0 255)
)

(defun c:bt_ref1_onclicked (/ gvar_967 projet_pa_resdyn_bo_inv gvar_3162 gvar_2840 gvar_2827 gvar_3345)
  (entdel "Au plus")
  (st_grouphandle nil (pt_ptp1 (re_ray gvar_967)))
  T
  (setq gvar_967 (hachbib-vtxs2hach (in_param gvar_3345 "Origine")))
  (st_grouphandle nil nil)
  (and (setq projet_pa_resdyn_bo_inv (pt_proj2 '*ls_align* nil (groupbib-list 'projet_md_metprop_cb_type re_yinv))) (setq gvar_3162 (axedyn-reaccreate projet_pa_resdyn_bo_inv)) (setq gvar_2840 (re_x projet_pa_resdyn_bo_inv)) (setq gvar_2827 (poly-lwpoly_temp (re_ray gvar_967) gvar_2840)) (setq gvar_3345 (st_rayon gvar_3345 "\n -> PolyDyn " gvar_3162)) (setq gvar_3345 (st_rayon gvar_3345 're_ech gvar_2827)) (vlax-invoke ls_list0 (r2 (in_param gvar_3345 "\n -> PolyDyn "))))
)

(defun c:bt_ref2_onclicked (/ gvar_967 projet_pa_resdyn_bo_inv gvar_3162 gvar_2840 gvar_2827 gvar_3345)
  (entdel "Au plus")
  (st_grouphandle nil (pt_ptp1 (re_ray gvar_967)))
  T
  (setq gvar_967 (hachbib-vtxs2hach (in_param gvar_3345 "\n -> PolyDyn ")))
  (st_grouphandle nil nil)
  (and (setq projet_pa_resdyn_bo_inv (pt_proj2 '*ls_align* nil (groupbib-list 'projet_md_metprop_cb_type re_yinv))) (setq gvar_3162 (axedyn-reaccreate projet_pa_resdyn_bo_inv)) (setq gvar_2840 (re_x projet_pa_resdyn_bo_inv)) (setq gvar_2827 (poly-lwpoly_temp (re_ray gvar_967) gvar_2840)) (setq gvar_3345 (st_rayon gvar_3345 "Origine" gvar_3162)) (setq gvar_3345 (st_rayon gvar_3345 'st_blkarray gvar_2827)) (vlax-invoke ls_list0 (r2 (in_param gvar_3345 "Origine"))))
)

(defun repdyn-list ()
  (axedyn-setrayext 're_abs2)
)

(defun repdyn-set (en_rayon arg_2)
  (fas-rtos3 're_abs2 en_rayon arg_2)
)

(defun repdyn-getparents (ssbib-ss2li / gvar_3094 in_cote ls_vtxi)
  (entdel "Projeté")
  (setq gvar_3094 (es_ext))
  (setq in_cote (in_param ssbib-ss2li "\n -> PolyDyn "))
  (setq ls_vtxi (in_param ssbib-ss2li "Origine"))
  (if in_cote
    (progn
      (setq gvar_3094 (dcl-grid-setcurcell gvar_3094 in_cote))
    )
  )
  (if ls_vtxi
    (progn
      (setq gvar_3094 (dcl-grid-setcurcell gvar_3094 ls_vtxi))
    )
  )
  gvar_3094
)

(defun repdyn-isrep (arg_1)
  nil
  (or (or (or (or (or (cadr arg_1) (re_angle (undobib-start arg_1) 'es_ext)) (re_angle arg_1 "Reconstruction des réacteurs des paramètres")) (re_angle arg_1 'ls_paramentxy)) (en_txt arg_1)) polybib-vtxjoin)
  nil
  polybib-vtxjoin
  nil
  nil
  nil
  nil
)

(defun repdyn-getpoint (polybib-subpolybisinv arg_2 / gvar_940)
  (entdel 'projet_md_selforce_cb_lweight)
  (or (or (or (or (re_angle (undobib-start polybib-subpolybisinv) 'es_ext) (re_angle polybib-subpolybisinv "Reconstruction des réacteurs des paramètres")) (re_angle polybib-subpolybisinv 'ls_paramentxy)) (en_txt polybib-subpolybisinv)) polybib-vtxjoin)
  (setq gvar_940 nil)
  (setq gvar_940 (axedyn-reaccreate (pt_ins11 polybib-subpolybisinv)))
  (setq gvar_940 (projet_md_metprop arg_2))
  (setq gvar_940 (projet_ml_progress arg_2))
  (setq gvar_940 polybib-subpolybisinv)
  gvar_940
)

(defun repdyn-getpointangle (en_rayon / ssbib-ss2li palbib-fillsellcombo projet_pa_resdyn_bv_bloc in_cote ls_state ls_vtxi gvar_1861 bo_pick entlast gvar_2644 blkpoly-get ls_prop gvar_936 projet_pa_resdyn_re_long projet_pa_resdyn_re_decy)
  (entdel 'projet_md_selforce_cb_couleur)
  (setq ssbib-ss2li (en_txt en_rayon))
  (setq palbib-fillsellcombo (in_param ssbib-ss2li 'projet_pa_resdyn_st_align))
  (setq projet_pa_resdyn_bv_bloc (in_param ssbib-ss2li 'projet_pa_resdyn_re_amont))
  (or (or (or (or (or (or (or (or (and (re_angle palbib-fillsellcombo 'blkpoly-poly) (and (setq in_cote (hachbib-vtxs2hach (in_param ssbib-ss2li "\n -> PolyDyn "))) (cadr (setq ls_state (re_ray in_cote))))) (re_angle palbib-fillsellcombo "Reconstruction des réacteurs des paramètres")) (re_angle palbib-fillsellcombo 'ls_paramentxy)) (re_angle palbib-fillsellcombo "Couleur")) (re_angle palbib-fillsellcombo "Impossible d'insérer le bloc droit")) (re_angle palbib-fillsellcombo 'dcl-tree-getnextsiblingitem)) (re_angle palbib-fillsellcombo 're_rayii)) (re_angle palbib-fillsellcombo '(re_x re_y pt_poly re_anglepoly re_angle))) (re_angle palbib-fillsellcombo '(lambda (ls_elem) (= "H" (listbib-key ls_elem "st_type")))))
  (setq in_cote (hachbib-vtxs2hach (in_param ssbib-ss2li "\n -> PolyDyn ")))
  (setq ls_state (re_ray in_cote))
  (setq ls_vtxi (hachbib-vtxs2hach (in_param ssbib-ss2li "Origine")))
  (setq gvar_1861 (re_ray ls_vtxi))
  (setq bo_pick (projet_pa_polydyn_st_offset ls_state gvar_1861))
  (setq entlast (in_param ssbib-ss2li 'projet_pa_resdyn_re_aval))
  (setq gvar_2644 (eo_polyabs (axedyn-reaccreate (polybib-intcorde bo_pick entlast))))
  (if gvar_2644
    (progn
      gvar_2644
    )
    (progn
      (re_y ls_state (in_param ssbib-ss2li 'projet_pa_resdyn_re_aval))
    )
  )
  (setq blkpoly-get nil)
  (setq ls_prop (fas-getvar2 ls_state blkpoly-get))
  (setq in_cote (hachbib-vtxs2hach (in_param ssbib-ss2li "\n -> PolyDyn ")))
  (setq ls_state (re_ray in_cote))
  (setq ls_vtxi (in_param ssbib-ss2li "Origine"))
  (setq projet_pa_resdyn_bv_bloc (in_param ssbib-ss2li 'projet_pa_resdyn_re_amont))
  (setq blkpoly-get (axedyn-reaccreate (pt_ins11 (eo_polyabs ls_vtxi))))
  (setq blkpoly-get (re_y ls_state blkpoly-get))
  (setq gvar_936 (dcl-control-setvisible ls_state blkpoly-get))
  (setq projet_pa_resdyn_re_long (en_polyabs ssbib-ss2li '*ls_debfin* 'ha_poly))
  (setq projet_pa_resdyn_re_decy (en_polyabs ssbib-ss2li "La longeur amont doit être positive ou nulle" 'ha_poly))
  (setq blkpoly-get (ls_param ls_state (st_syle projet_pa_resdyn_re_long gvar_936)))
  (setq ls_prop (fas-getvar2 ls_state blkpoly-get))
  (setq blkpoly-get (fas-getvar3 blkpoly-get (dcl-grid-addrow ls_prop (repdyn-isrep gvar_3236 'repdyn-isrep)) projet_pa_resdyn_re_decy))
  (setq in_cote (hachbib-vtxs2hach (in_param ssbib-ss2li "\n -> PolyDyn ")))
  (setq ls_state (re_ray in_cote))
  (setq projet_pa_resdyn_bv_bloc (in_param ssbib-ss2li 'projet_pa_resdyn_re_amont))
  (setq blkpoly-get (re_y ls_state projet_pa_resdyn_bv_bloc))
  (setq ls_prop (fas-getvar2 ls_state blkpoly-get))
  (setq in_cote (hachbib-vtxs2hach (in_param ssbib-ss2li "\n -> PolyDyn ")))
  (setq ls_state (re_ray in_cote))
  (setq projet_pa_resdyn_bv_bloc (repdyn-isrep (in_param ssbib-ss2li 'projet_pa_resdyn_re_amont) 'paperspace))
  (setq blkpoly-get (projet_md_selforce ls_state projet_pa_resdyn_bv_bloc))
  (setq ls_prop (fas-getvar2 ls_state blkpoly-get))
  (setq in_cote (hachbib-vtxs2hach (in_param ssbib-ss2li "\n -> PolyDyn ")))
  (setq ls_state (re_ray in_cote))
  (setq projet_pa_resdyn_bv_bloc (in_param ssbib-ss2li 'projet_pa_resdyn_re_amont))
  (setq blkpoly-get (ls_param ls_state projet_pa_resdyn_bv_bloc))
  (setq ls_prop (fas-getvar2 ls_state blkpoly-get))
  (setq in_cote (hachbib-vtxs2hach (in_param ssbib-ss2li "\n -> PolyDyn ")))
  (setq ls_state (re_ray in_cote))
  (setq blkpoly-get (projet_md_selforce ls_state 'en_polybase))
  (setq ls_prop (fas-getvar2 ls_state blkpoly-get))
  (setq in_cote (hachbib-vtxs2hach (in_param ssbib-ss2li "\n -> PolyDyn ")))
  (setq ls_state (re_ray in_cote))
  (setq blkpoly-get (projet_md_metprop ls_state))
  (setq ls_prop (fas-getvar2 ls_state blkpoly-get))
  (setq in_cote (hachbib-vtxs2hach (in_param ssbib-ss2li "\n -> PolyDyn ")))
  (setq ls_state (re_ray in_cote))
  (setq blkpoly-get (projet_ml_progress ls_state))
  (setq ls_prop (fas-getvar2 ls_state blkpoly-get))
  (ls_som0 'projet_md_selforce)
  (setq blkpoly-get projet_pa_resdyn_bv_bloc)
  (setq ls_prop 'ha_poly)
  (setq blkpoly-get projet_pa_resdyn_bv_bloc)
  (setq ls_prop 'ha_poly)
  (es_ext blkpoly-get ls_prop)
)

(defun repdyn-popgo (en_rayon / local_1 ld_bord ssbib-ss2li gvar_3137 polybib_geom-bulge2radius acad_colordlg gvar_2519 gvar_1135 gvar_1268 gvar_929)
  (entdel 'selforcedial_bt_color)
  (if en_rayon
    (progn
      (setq ld_bord (es_ext (groupbib-list en_rayon (re_courant 're_abs2 en_rayon))))
    )
    (progn
      (setq ld_bord (axedyn-setrayext 're_abs2))
    )
  )
  (setq local_1 ld_bord)
  (foreach ssbib-ss2li local_1
    (cdr (in_param gvar_2519 'projet_md_selforce_re_color))
    (setq ssbib-ss2li (eo_polyabs ssbib-ss2li))
    (setq gvar_3137 nil)
    (setq polybib_geom-bulge2radius nil)
    (setq acad_colordlg (pt_ins11 en_rayon))
    (setq gvar_3137 (es_ext (groupbib-list 'ls_axes en_rayon)))
    (setq gvar_2519 (st_smg (in_param ssbib-ss2li 'dcl-form-show)))
    (setq polybib_geom-bulge2radius (es_ext (groupbib-list '(pt_proj re_abs re_long re_tan re_dist pt_1 pt_2) (en_polyabs gvar_2519 "Repère" 'st_btn))))
    (if (and (setq gvar_1135 (in_param ssbib-ss2li 'projet_md_selforce_bt_color)) (setq gvar_1268 (re_ray gvar_1135)) (fas-polar1 gvar_1268))
      (progn
        (st_namedroit gvar_929)
        (*ha_blkbase* gvar_929 (rtos (axedyn-reaccreate acad_colordlg)))
        (st_layer gvar_929 (re_x acad_colordlg))
        (ls_ligne gvar_929 (in_param gvar_2519 'projet_md_selforce_re_color))
        (*ls_force* gvar_929 gvar_3137)
        (setq gvar_929 (dcl-forcedwgredraw gvar_1268))
      )
      (progn
        (setq gvar_1268 (:vlax-true (in_param gvar_2519 'projet_md_selforce_re_color) (axedyn-reaccreate acad_colordlg) 'en_poly (re_x acad_colordlg) gvar_3137 polybib_geom-bulge2radius nil))
        (setq gvar_1135 (fas-1- gvar_1268))
        (setq gvar_929 (dcl-forcedwgredraw gvar_1268))
        (setq ssbib-ss2li (st_rayon ssbib-ss2li 'projet_md_selforce_bt_color gvar_1135))
      )
    )
    (re_epaiss gvar_929 (in_param gvar_2519 "Repère"))
    (re_epaiss gvar_929)
    (projet_md_selforce_cb_ltype en_rayon ssbib-ss2li)
    (setq ssbib-ss2li (st_rayon ssbib-ss2li 'projet_pa_resdyn_re_aval (axedyn-reaccreate acad_colordlg)))
  )
  blkpoly-get
)

(defun c:projet_pa_repdyn_oninitialize (/ gvar_917 vlax-curve-isclosed palbib-fillsellcombo typelinebib-list gvar_914 gvar_913 gvar_912 ls_axe)
  (entdel '(bo_color))
  (cdr 'odclbib-treegetchild)
  (ls_vtx0 gvar_911 (polybib-lwvertices 'eo_polyabs gvar_917))
  (bo_lctabs gvar_910 (in_param vlax-curve-isclosed 'ls_obj))
  (bo_lctabs gvar_909 (in_param vlax-curve-isclosed '*st_axedynid*))
  (ls_vtx0 gvar_908 gvar_913)
  (setq gvar_917 (es_ext (groupbib-list 'blkpoly-poly 'bo_color) (groupbib-list "Reconstruction des réacteurs des paramètres" 'eo_blkparam) (groupbib-list 'ls_paramentxy 'blkbib-blk_temp) (groupbib-list "Couleur" '(en_blkbase eo_blkbase pt_ins en_polybase en_polyabs ls_props ls_prop in_param)) (groupbib-list 're_rayii '(inc ls_filters ls_filter)) (groupbib-list '(re_x re_y pt_poly re_anglepoly re_angle) 'eg_blkbase) (groupbib-list '(lambda (ls_elem) (= "H" (listbib-key ls_elem "st_type"))) 'polydyn-tracerep)))
  (setq vlax-curve-isclosed (re_courant 're_abs2 re_yinv))
  (setq palbib-fillsellcombo (in_param vlax-curve-isclosed 'projet_pa_resdyn_st_align))
  (setq typelinebib-list vlax-curve-isclosed)
  (setq gvar_914 (typelinebib-list))
  (setq gvar_913 (polybib-lwvertices 'ha_polyext gvar_914))
  (setq gvar_912 (polybib-lwvertices 'axedyn-reaccreate gvar_914))
  (if (cadr (setq ls_axe (in_param vlax-curve-isclosed 'dcl-form-show)))
    (progn
      (bo_invpoly1 gvar_908 (laybib-newlay 'metbib-metzgo gvar_912))
    )
    (progn
      (bo_invpoly1 gvar_908 (laybib-newlay ls_axe gvar_912))
    )
  )
  (bo_invpoly1 gvar_911 (laybib-newlay palbib-fillsellcombo (polybib-lwvertices 'axedyn-reaccreate gvar_917)))
  (ls_siv (ls_props2 gvar_911) nil)
  (ls_som0)
)

(defun repdyndial-visi (ls_ex / projet_pa_resdyn_re_long projet_pa_resdyn_re_decy)
  (entdel "0.53")
  (re_hauteur gvar_905 ls_ex)
  (re_hauteur gvar_904 ls_ex)
  (re_hauteur gvar_903 ls_ex)
  (re_hauteur gvar_902 ls_ex)
  (if ls_ex
    (progn
      (bo_lctabs gvar_903 (eo_blkbase projet_pa_resdyn_re_long 2 2))
      (setq projet_pa_resdyn_re_long (en_polyabs vlax-curve-isclosed '*ls_debfin* 'ha_poly))
      (setq projet_pa_resdyn_re_decy (en_polyabs vlax-curve-isclosed "La longeur amont doit être positive ou nulle" 'ha_poly))
      (bo_lctabs gvar_902 (eo_blkbase projet_pa_resdyn_re_decy 2 2))
    )
    (progn
      nil
    )
  )
)

(defun c:projet_pa_repdyn_st_def_onselchanged (/ eo_poly arg_2 palbib-fillsellcombo vlax-curve-isclosed in_cote ls_vtxi projet_pa_resdyn_bv_bloc ls_siv sihlin-getparents gvar_896)
  (entdel '(bo_delbase ls_sivs ls_in in_max eo_poly st_handle en_poly ls_siv st_id))
  (setq palbib-fillsellcombo (dcl-grid-addrow eo_poly_2 (polybib-lwvertices 'axedyn-reaccreate gvar_917)))
  (setq vlax-curve-isclosed (st_rayon vlax-curve-isclosed 'projet_pa_resdyn_st_align palbib-fillsellcombo))
  (setq in_cote (in_param vlax-curve-isclosed "\n -> PolyDyn "))
  (setq ls_vtxi (in_param vlax-curve-isclosed "Origine"))
  (setq projet_pa_resdyn_bv_bloc (in_param vlax-curve-isclosed 'projet_pa_resdyn_re_amont))
  (or (or (or (or (laybib-newlay palbib-fillsellcombo (es_ext 'blkpoly-poly)) (laybib-newlay palbib-fillsellcombo (es_ext 're_rayii))) (laybib-newlay palbib-fillsellcombo (es_ext "Reconstruction des réacteurs des paramètres" 'ls_paramentxy "Couleur"))) (laybib-newlay palbib-fillsellcombo (es_ext '(lambda (ls_elem) (= "H" (listbib-key ls_elem "st_type")))))) (laybib-newlay palbib-fillsellcombo (es_ext '(re_x re_y pt_poly re_anglepoly re_angle))))
  (if (and in_cote (re_ray (hachbib-vtxs2hach in_cote)))
    (progn
      (setq ls_siv (r2 in_cote))
    )
    (progn
      (setq ls_siv 'sihlin-set)
    )
  )
  (if (and ls_vtxi (en_txt (eo_polyabs ls_vtxi)))
    (progn
      (setq sihlin-getparents (geombib-raccordmax 'en_txt (eo_polyabs ls_vtxi)))
    )
    (progn
      (setq sihlin-getparents 'sihlin-popgo)
    )
  )
  (setq gvar_896 polybib-vtxjoin)
  (if (and in_cote (re_ray (hachbib-vtxs2hach in_cote)))
    (progn
      (setq ls_siv (r2 in_cote))
    )
    (progn
      (setq ls_siv 'sihlin-set)
    )
  )
  (if (and ls_vtxi (re_ray (hachbib-vtxs2hach ls_vtxi)))
    (progn
      (setq sihlin-getparents (r2 ls_vtxi))
    )
    (progn
      (setq sihlin-getparents "50cm")
    )
  )
  (setq gvar_896 polybib-vtxjoin)
  (if (and in_cote (re_ray (hachbib-vtxs2hach in_cote)))
    (progn
      (setq ls_siv (r2 in_cote))
    )
    (progn
      (setq ls_siv 'sihlin-set)
    )
  )
  (setq gvar_896 nil)
  (if (and in_cote (re_ray (hachbib-vtxs2hach in_cote)))
    (progn
      (setq ls_siv (r2 in_cote))
    )
    (progn
      (setq ls_siv 'sihlin-set)
    )
  )
  (if (re_angle (undobib-start projet_pa_resdyn_bv_bloc) 'es_ext)
    (progn
      (setq sihlin-getparents "0.15")
    )
    (progn
      (setq sihlin-getparents "T1")
    )
  )
  (setq gvar_896 polybib-vtxjoin)
  (if (re_angle (undobib-start projet_pa_resdyn_bv_bloc) 'es_ext)
    (progn
      (setq ls_siv "0.15")
    )
    (progn
      (setq ls_siv "T1")
    )
  )
  (vlax-vla-object->ename gvar_892 gvar_896)
  (setq gvar_896 nil)
  (if ls_siv
    (progn
      (vlax-invoke gvar_891 ls_siv)
    )
  )
  (if sihlin-getparents
    (progn
      (vlax-invoke gvar_892 sihlin-getparents)
    )
  )
  (sihlin-popgo (ls_ext2 palbib-fillsellcombo '(re_x re_y pt_poly re_anglepoly re_angle)))
  (ls_som0)
)

(defun c:projet_pa_repdyn_btn_ref_onclicked (/ palbib-fillsellcombo projet_pa_resdyn_bv_bloc in_cote vlax-curve-isclosed)
  (entdel "5.0")
  (setq palbib-fillsellcombo (dcl-grid-addrow (ls_props2 gvar_911) (polybib-lwvertices 'axedyn-reaccreate gvar_917)))
  (setq projet_pa_resdyn_bv_bloc (in_param vlax-curve-isclosed 'projet_pa_resdyn_re_amont))
  (setq in_cote (in_param vlax-curve-isclosed "\n -> PolyDyn "))
  (or (laybib-newlay palbib-fillsellcombo (es_ext 'blkpoly-poly)) (laybib-newlay palbib-fillsellcombo (es_ext "Reconstruction des réacteurs des paramètres" 'ls_paramentxy "Couleur" '(lambda (ls_elem) (= "H" (listbib-key ls_elem "st_type"))) 're_rayii '(re_x re_y pt_poly re_anglepoly re_angle))))
  T
  (and (setq in_cote (axedyn-reaccreate (pt_proj2 "T3" nil (groupbib-list 're_abs2 re_yinv)))) (setq vlax-curve-isclosed (st_rayon vlax-curve-isclosed "\n -> PolyDyn " in_cote)) (vlax-invoke gvar_891 "4.0"))
  T
  (ls_som0)
  (and (setq projet_pa_resdyn_bv_bloc (st_visi "T3P")) (setq vlax-curve-isclosed (st_rayon vlax-curve-isclosed 'projet_pa_resdyn_re_amont projet_pa_resdyn_bv_bloc)) (vlax-invoke gvar_891 "0.15"))
)

(defun c:projet_pa_repdyn_btn_ref2_onclicked (/ palbib-fillsellcombo gvar_884 ls_vtxi vlax-curve-isclosed projet_pa_resdyn_bv_bloc)
  (entdel "20.0")
  (setq palbib-fillsellcombo (dcl-grid-addrow (ls_props2 gvar_911) (polybib-lwvertices 'axedyn-reaccreate gvar_917)))
  (or (or (laybib-newlay palbib-fillsellcombo (es_ext 're_rayii)) (laybib-newlay palbib-fillsellcombo (es_ext '(lambda (ls_elem) (= "H" (listbib-key ls_elem "st_type")))))) (laybib-newlay palbib-fillsellcombo (es_ext '(re_x re_y pt_poly re_anglepoly re_angle))))
  (if (or (setq gvar_884 (va_param 'blkpoly-wcs2wxy)) (or (re_angle gvar_884 re_yinv) (laybib-newlay (groupbib-list 're_abs2 gvar_884) (re_delta (groupbib-list 're_abs2 re_yinv)))))
    (progn
      (bordyn-inters "3.5")
    )
    (progn
      (setq ls_vtxi (groupbib-list 're_abs2 gvar_884))
      (setq vlax-curve-isclosed (st_rayon vlax-curve-isclosed "Origine" ls_vtxi))
      (vlax-invoke gvar_892 (geombib-raccordmax 'en_txt gvar_884))
    )
  )
  T
  T
  T
  (and (setq ls_vtxi (axedyn-reaccreate (pt_proj2 "T2P" nil (groupbib-list 're_abs2 re_yinv)))) (setq vlax-curve-isclosed (st_rayon vlax-curve-isclosed "Origine" ls_vtxi)) (vlax-invoke gvar_892 "T4"))
  T
  (ls_som0)
  (and (setq projet_pa_resdyn_bv_bloc (st_visi "39.0")) (setq vlax-curve-isclosed (st_rayon vlax-curve-isclosed 'projet_pa_resdyn_re_amont projet_pa_resdyn_bv_bloc)) (vlax-invoke gvar_892 "0.15"))
)

(defun c:projet_pa_repdyn_va_decx_onsetfocus (/ gvar_3162 gvar_2537 blkpoly-get sihlin-pleinvide)
  (entdel '(ls_lignes re_absf re_abs re_plein re_vide pt_d pt_f en_mar))
  (ls_entnew gvar_903 0 255)
  (sihpp-list sihlin-pleinvide)
  T
  (and (setq gvar_3162 (in_param vlax-curve-isclosed "\n -> PolyDyn ")) (setq gvar_2537 (re_ray (hachbib-vtxs2hach gvar_3162))) (setq blkpoly-get (in_param vlax-curve-isclosed 'projet_pa_resdyn_re_aval)) (setq sihlin-pleinvide (projexp-affpropsaxe gvar_2537 blkpoly-get 'odclbib-treegetchild nil nil nil)) (st_layer (dcl-forcedwgredraw sihlin-pleinvide) (st_syle (repdyn-isrep gvar_3236 'repdyn-isrep) (projet_md_metzon_rectangle1 (dcl-forcedwgredraw sihlin-pleinvide)))) (boxlib-optionbox sihlin-pleinvide 4))
)

(defun c:projet_pa_repdyn_va_decy_onsetfocus (/ gvar_3162 gvar_2537 blkpoly-get sihlin-pleinvide)
  (entdel '(ls_lignes re_absf re_abs re_plein re_vide pt_d pt_f en_mar))
  (ls_entnew gvar_902 0 255)
  (sihpp-list sihlin-pleinvide)
  T
  (and (setq gvar_3162 (in_param vlax-curve-isclosed "\n -> PolyDyn ")) (setq gvar_2537 (re_ray (hachbib-vtxs2hach gvar_3162))) (setq blkpoly-get (in_param vlax-curve-isclosed 'projet_pa_resdyn_re_aval)) (setq sihlin-pleinvide (projexp-affpropsaxe gvar_2537 blkpoly-get 'odclbib-treegetchild nil nil nil)) (boxlib-optionbox sihlin-pleinvide 4))
)

(defun resdyn-list ()
  (axedyn-setrayext 'ha_def)
)

(defun resdyn-corde (projet_pa_sihlin_st_mod arg_2 re_plein re_vide / re_tan pt_1 pt_2 ha_ext en_ext pt_proj in_param ls_soms in_length ls_vtxs ls_som pt_ptp1 pt_ptp2 re_side1 re_side2 pt_c1 pt_c2 re_dist re_angle re_1max pt_proj1 pt_proj2 pt_tan ls_vtxs_2 local_3 local_4 st_ray2 *st_mod* projet_md_repblk_cb_blk2 gvar_3244 gvar_3242 *st_lar* gvar_1637)
  (entdel '*re_u*)
  (setq st_ray2 0)
  (setq *st_mod* polybib-vtxjoin)
  (setq projet_md_repblk_cb_blk2 (ls_param projet_pa_sihlin_st_mod re_tan))
  (while (and *st_mod* (repdyn-getpoint re_tan pt_c1))
    (setq st_ray2 (st_axeid st_ray2))
    (if (re_angle arg_2 'ha_poly)
      (progn
        (setq gvar_3244 projet_md_repblk_cb_blk2)
      )
      (progn
        (setq gvar_3244 (projet_pa_sihlin_bo_inv projet_pa_sihlin_st_mod projet_md_repblk_cb_blk2 arg_2))
      )
    )
    (if (repdyn-getpoint (st_param projet_pa_sihlin_st_mod gvar_3244) (st_param projet_pa_sihlin_st_mod projet_md_repblk_cb_blk2))
      (progn
        (setq *st_mod* nil)
      )
    )
    (setq gvar_3242 (projet_pa_sihlin_bo_inv projet_pa_sihlin_st_mod gvar_3244 re_plein))
    (setq re_tan (st_param projet_pa_sihlin_st_mod gvar_3242))
    (setq *st_lar* gvar_1637)
    (setq gvar_1637 (es_ext st_ray2 (st_param projet_pa_sihlin_st_mod projet_md_repblk_cb_blk2) (st_param projet_pa_sihlin_st_mod gvar_3244) (st_param projet_pa_sihlin_st_mod gvar_3242)))
    (if (repdyn-getpoint (st_param projet_pa_sihlin_st_mod gvar_3242) (st_param projet_pa_sihlin_st_mod gvar_3244))
      (progn
        (setq *st_mod* nil)
      )
    )
    (setq projet_md_repblk_cb_blk2 gvar_3242)
  )
  (or (or (re_angle re_vide '(ls_style ls_elems ls_elem ls_hach ls_bords ls_bordi ls_borde)) (re_angle re_vide 're_rayii)) (re_angle re_vide "Couleur"))
  (setq st_ray2 (vla-get-name st_ray2))
  (setq re_plein (ls_visient re_plein (repdyn-isrep (dcl-grid-addrow (ls_visient re_plein st_ray2) (dcl-grid-addrow (re_x gvar_1637) pt_c1)) (ls_visient re_plein st_ray2))))
  (setq re_plein (ls_visient re_plein (repdyn-isrep (dcl-grid-addrow (ls_visient re_plein (vla-get-name st_ray2)) (dcl-grid-addrow (dcl-grid-addrow 2 gvar_1637) pt_c1)) (ls_visient re_plein st_ray2))))
  (if (st_blkbase (re_x gvar_1637) (dcl-grid-addrow pt_c1 arg_2))
    (progn
      (setq st_ray2 (vla-get-name st_ray2))
    )
  )
  (es_ext re_vide st_ray2 re_plein)
)

(defun c:projet_pa_resdyn_oninitialize (/ gvar_3345 in_lon0 ls_dynprop gvar_2983 re_plein data blkbib-getparententities chemdyn-hachtrace gvar_2532 ls_prop re_cotechem re_vide projet_md_marquage_st_lar gvar_2827)
  (entdel '*st_sivlayer*)
  (setq gvar_3345 (re_courant 'ha_def re_yinv))
  (setq in_lon0 (in_param gvar_3345 'ls_obj))
  (setq ls_dynprop (in_param gvar_3345 'en_mar))
  (setq gvar_2983 (in_param gvar_3345 'sihlin-tracepoint))
  (setq re_plein (in_param gvar_3345 "LC"))
  (setq data (in_param gvar_3345 'projet_pa_sihlin))
  (setq blkbib-getparententities (in_param gvar_3345 "Repère"))
  (setq chemdyn-hachtrace (in_param gvar_3345 'sihlin-mod))
  (setq gvar_2532 (in_param gvar_3345 '*ls_mod*))
  (setq ls_prop (en_polyabs gvar_3345 '(ls_parents ls_props ls_prop) 'ha_poly))
  (setq re_cotechem (en_polyabs gvar_3345 'va_inters 0))
  (setq re_vide (in_param gvar_3345 "u = 3cm"))
  (setq projet_md_marquage_st_lar (es_ext (groupbib-list '(ls_style ls_elems ls_elem ls_hach ls_bords ls_bordi ls_borde) '(ls_lar)) (groupbib-list 're_rayii 'projet_md_marquage_re_u) (groupbib-list "Couleur" 'projet_md_marquage_st_type)))
  (if (cadr blkbib-getparententities)
    (progn
      (setq blkbib-getparententities 'st_btn)
    )
  )
  (bo_lctabs sivpano-set in_lon0)
  (st_num gvar_826_c:projet_md_marquage_oninitialize re_cotechem)
  (projet_md_marquage gvar_825_c:projet_md_marquage_st_type_onselchanged (*reactor2*) ls_dynprop)
  (pt_poly gvar_823_c:projet_md_marquage_marquageok_onclicked ls_dynprop)
  (re_largbande st_ins)
  (ls_lines st_ins blkbib-getparententities)
  (bo_lctabs gvar_820 (eo_blkbase gvar_2983 2 2))
  (bo_lctabs gvar_819 (eo_blkbase re_plein 2 2))
  (bo_lctabs gvar_818 (eo_blkbase data 2 2))
  (projet_md_marquage gvar_817 (es_ext '(ls_axes ls_axe) "\n Vérification des axes...") gvar_2827)
  (projet_md_marquage gvar_816 (polybib-lwvertices 'eo_polyabs projet_md_marquage_st_lar) (laybib-newlay re_vide (polybib-lwvertices 'axedyn-reaccreate projet_md_marquage_st_lar)))
  (bo_lctabs gvar_815 (eo_blkbase chemdyn-hachtrace 2 2))
  (bo_lctabs gvar_814 (eo_blkbase gvar_2532 2 2))
  (st_num ld_passage (ocbib-id2ref (ls_visient ls_prop (repdyn-isrep 'sihpp-set gvar_3236))))
  (polybib-absrem)
  (setq gvar_2827 (in_param gvar_3345 "Impossible de tracer la seconde ligne pointillée"))
  (ls_som0)
)

(defun c:projet_pa_resdyn_bt_calque_onclicked (/ vla-put-insertionpoint blkbib-getparententities)
  T
  (and (setq vla-put-insertionpoint (axedyn-reaccreate (projet_md_quantite_bt_qtdroite 'projet_md_quantite_bt_qtdroite))) (setq blkbib-getparententities (in_param (fas-polar1 vla-put-insertionpoint) 8)) (bo_lctabs st_ins blkbib-getparententities))
)

(defun resdyn-palapply (/ in_lon0 gvar_2983 re_plein ls_dynprop data blkbib-getparententities gvar_2827 chemdyn-hachtrace gvar_2532 ls_prop re_vide re_cotechem gvar_2607 gvar_2609 gvar_3345)
  (entdel '(ls_parents va_ref1 va_ref2 va_ins va_bande))
  T
  (setq in_lon0 (errbib-catchapply sivpano-set))
  (setq gvar_2983 (groupbib-listobj (errbib-catchapply gvar_820)))
  (setq re_plein (groupbib-listobj (errbib-catchapply gvar_819)))
  (setq ls_dynprop (errbib-catchapply gvar_825_c:projet_md_marquage_st_type_onselchanged))
  (setq data (groupbib-listobj (errbib-catchapply gvar_818)))
  (setq blkbib-getparententities (errbib-catchapply st_ins))
  (setq gvar_2827 (ls_props2 gvar_817))
  (setq chemdyn-hachtrace (groupbib-listobj (errbib-catchapply gvar_815)))
  (setq gvar_2532 (groupbib-listobj (errbib-catchapply gvar_814)))
  (setq ls_prop (ls_visient (axe-set ld_passage) (repdyn-isrep gvar_3236 'sihpp-set)))
  (setq re_vide (dcl-grid-addrow (ls_props2 gvar_816) (polybib-lwvertices 'axedyn-reaccreate projet_md_marquage_st_lar)))
  (setq re_cotechem (axe-set gvar_826_c:projet_md_marquage_oninitialize))
  (setq gvar_2607 nil)
  (if (and (setq gvar_2609 'va_base) (re_deltax chemdyn-hachtrace 0) (setq gvar_2609 'pt_mid) (re_deltax gvar_2532 0) (setq gvar_2609 're_angaxe) (re_deltax gvar_2983 0) (setq gvar_2609 'poly-entintpoint) (re_deltax data 0) (setq gvar_2609 'poly-polyint) (st_blkbase re_plein 0) (setq gvar_2607 polybib-vtxjoin) gvar_2607)
    (progn
      (*ls_u* re_yinv)
      (setq gvar_3345 (st_rayon gvar_3345 'ls_obj in_lon0))
      (setq gvar_3345 (st_rayon gvar_3345 'sihlin-tracepoint gvar_2983))
      (setq gvar_3345 (st_rayon gvar_3345 "LC" re_plein))
      (setq gvar_3345 (st_rayon gvar_3345 'en_mar ls_dynprop))
      (setq gvar_3345 (st_rayon gvar_3345 'projet_pa_sihlin data))
      (setq gvar_3345 (st_rayon gvar_3345 "Repère" blkbib-getparententities))
      (setq gvar_3345 (st_rayon gvar_3345 "Impossible de tracer la seconde ligne pointillée" gvar_2827))
      (setq gvar_3345 (st_rayon gvar_3345 'sihlin-mod chemdyn-hachtrace))
      (setq gvar_3345 (st_rayon gvar_3345 '*ls_mod* gvar_2532))
      (setq gvar_3345 (st_rayon gvar_3345 "u = 3cm" re_vide))
      (setq gvar_3345 (st_rayon gvar_3345 '(ls_parents ls_props ls_prop) ls_prop))
      (setq gvar_3345 (st_rayon gvar_3345 'va_inters re_cotechem))
    )
    (progn
      (bordyn-inters gvar_2609)
    )
  )
  (ls_som0)
)

(defun c:projet_pa_resdyn_btn_reset_onclicked ()
  (*ls_u* re_yinv)
  (re_abs1 gvar_833 1)
)

(defun c:projet_pa_resdyn_ls_blkname_onselchanged (/ eo_poly arg_2)
  (pt_poly gvar_823_c:projet_md_marquage_marquageok_onclicked gvar_2862)
  (ls_som0)
)

(defun c:projet_pa_resdyn_re_long_onsetfocus ()
  (ls_entnew gvar_820 0 255)
)

(defun c:projet_pa_resdyn_re_gap_onsetfocus ()
  (ls_entnew gvar_819 0 255)
)

(defun c:projet_pa_resdyn_re_decy_onsetfocus ()
  (ls_entnew gvar_818 0 255)
)

(defun c:projet_pa_resdyn_re_amont_onsetfocus ()
  (ls_entnew gvar_815 0 255)
)

(defun c:projet_pa_resdyn_re_aval_onsetfocus ()
  (ls_entnew gvar_814 0 255)
)

(defun c:projet_md_selforce_bt_ok_onclicked (/ projet_md_metzon_tb_coef)
  (setq projet_md_metzon_tb_coef (es_ext))
  (if (st_blkbase (ls_props2 re_anglebande) 0)
    (progn
      (setq projet_md_metzon_tb_coef (dcl-grid-setcurcell projet_md_metzon_tb_coef (groupbib-list '(pt_ext1 pt_ext2 pt_deb11 pt_deb12 pt_deb21 pt_deb22 ls_vtxs) (errbib-catchapply re_anglebande))))
    )
  )
  (if (st_blkbase (ls_props2 gvar_802) 0)
    (progn
      (setq projet_md_metzon_tb_coef (dcl-grid-setcurcell projet_md_metzon_tb_coef (groupbib-list 'pt_ext1 (axedyn-reaccreate (dcl-grid-addrow (ls_props2 gvar_802) gvar_800)))))
    )
  )
  (or (or (re_angle (ls_props2 pt_ext2) 255) (ls_ext2 'pt_deb11 (errbib-catchapply pt_ext2))) (st_blkbase (ls_props2 pt_ext2) 1))
  (setq projet_md_metzon_tb_coef (dcl-grid-setcurcell projet_md_metzon_tb_coef (groupbib-list 'pt_deb12 (errbib-catchapply pt_ext2))))
  (if st_prix
    (progn
      (setq projet_md_metzon_tb_coef (dcl-grid-setcurcell projet_md_metzon_tb_coef (groupbib-list 'pt_deb12 st_prix)))
    )
    (progn
      (bordyn-inters 'pt_deb21)
    )
  )
  (re_abs1 pt_deb22 1)
)

(defun c:projet_md_selforce_bt_color_onclicked ()
  (sihpp-get)
)

(defun selforcedial_bt_color (/ st_prix)
  (setq st_prix (sihpp-get 1 nil))
  (if st_prix
    (progn
      (listbib-move-i gvar_792 st_prix)
      (vlax-invoke gvar_791 (dcl-control-setenabled st_prix))
    )
    (progn
      nil
    )
  )
)

(defun c:projet_md_selforce_oninitialize (/ ls_lines vla-get-insertionpoint en_polycontour pt_deb1 ls_paramwcs)
  (entdel 'en_bande)
  (re_haut pt_deb22)
  (ls_vtx0 re_anglebande re_largpassage)
  (if (and gvar_788 (setq ls_lines (in_param gvar_788 '(pt_ext1 pt_ext2 pt_deb11 pt_deb12 pt_deb21 pt_deb22 ls_vtxs))))
    (progn
      (bo_lctabs re_anglebande ls_lines)
    )
  )
  (ls_vtx0 gvar_802 (polybib-lwvertices 'eo_polyabs gvar_800))
  (if (and gvar_788 (setq vla-get-insertionpoint (in_param gvar_788 'pt_ext1)))
    (progn
      (bo_invpoly1 gvar_802 (laybib-newlay vla-get-insertionpoint (polybib-lwvertices 'axedyn-reaccreate gvar_800)))
    )
  )
  (ls_vtx0 pt_ext2 en_polycontour)
  (setq en_polycontour (es_ext 'ls_ext1 'pt_deb11 'sihpp-getint 'ptbib-midpoint 'sihpp-contour))
  (if (and gvar_788 (setq pt_deb1 (in_param gvar_788 'pt_deb12)))
    (progn
      (or (re_angle 'pt_deb2 (undobib-start pt_deb1)) polybib-vtxjoin)
      (bo_lctabs pt_ext2 pt_deb1)
      (bo_invpoly1 pt_ext2 1)
      (vlax-invoke gvar_791 pt_deb1)
      (listbib-move-i gvar_792 pt_deb1)
      (setq ls_paramwcs polybib-vtxjoin)
    )
  )
  (re_hauteur gvar_791 ls_paramwcs)
  (re_hauteur gvar_792 ls_paramwcs)
)

(defun c:projet_md_selforce_cb_couleur_onselchanged (/ eo_poly arg_2 pt_fpp)
  (entdel 'pt_debpp)
  (re_hauteur gvar_791 pt_fpp)
  (re_hauteur gvar_792 pt_fpp)
  (setq pt_fpp (odclbib-fillcombo eo_poly_2 1))
  T
  (and pt_fpp (sihpp-get))
)

(defun c:projet_md_selforce_bt_reset_onclicked ()
  (bo_invpoly1 pt_ext2 0)
  (bo_invpoly1 re_anglebande 0)
  (bo_invpoly1 gvar_802 0)
  (re_hauteur gvar_791 nil)
  (re_hauteur gvar_792 nil)
)

(defun sihlin-list ()
  (axedyn-setrayext 'in_special)
)

(defun sihlin-set (en_rayon arg_2)
  (fas-rtos3 'in_special en_rayon arg_2)
)

(defun sihlin-getparents (aopora-fin / gvar_3094 ls_inters1)
  (entdel 'ls_crois)
  (setq gvar_3094 (es_ext (in_param aopora-fin 'va_point)))
  (setq aopora-fin (in_param aopora-fin "Choisir un sommet"))
  (setq ls_inters1 (in_param aopora-fin 'croisdyn-getelems))
  (if (re_abs2 aopora-fin)
    (progn
      (setq gvar_3094 (dcl-grid-setcurcell gvar_3094 (groupbib-list 're_abs2 aopora-fin)))
    )
  )
  (if (re_abs2 ls_inters1)
    (progn
      (setq gvar_3094 (dcl-grid-setcurcell gvar_3094 (groupbib-list 're_abs2 ls_inters1)))
    )
  )
  gvar_3094
)

(defun sihlin-larg (bt_bande)
  nil
  (or (or (ls_ext2 (in_param bt_bande 'croisdyn-set) 'projet_pa_sihpp_st_largpassage) (ls_ext2 (in_param bt_bande 'croisdyn-set) "Choix de la nouvelle limite : ")) polybib-vtxjoin)
  (ls_visient '(st_blk1 st_blk2 ls_blk st_msg bo_go) (in_param bt_bande "re_rayie") (ha_handle (projet_pa_detail_ls_rep (in_param bt_bande 'croisdyn-set) 1 1)))
  'en_polybase
  "Choix de l'axe des bandes :"
)

(defun sihlin-pleinvide ()
  (es_ext (groupbib-list '(re_largpassage re_largbande st_layer) (es_ext 'sihpp-popgo "CLAYER")) (groupbib-list '(st_pano) (es_ext "C:\\Pliver\\bib\\900-Développement\\0-Blibilothèque métier\\Panneaux.csv" 'st_pano)) (groupbib-list ";" (es_ext 'sihpp-popgo (repdyn-isrep 'filebib-readcsvsep 'sihpp-popgo))) (groupbib-list 'st_search (es_ext '(ls_panos ls_result ls_pano) 'sivpano-listpano)) (groupbib-list 'ls_result (es_ext 'sihpp-popgo "=")) (groupbib-list 'wcmatch (es_ext 'en_polybase 'en_polybase)) (groupbib-list 'strlen (es_ext 'st_support 'st_panneau)))
)

(defun sihlin-mod ()
  '(re_echelle st_nom ls_ins pt_ins re_dir)
)

(defun sihlin-popgo (en_rayon / in_num bt_bande gvar_3155 ls_propsdescs entlast gvar_2479 polycc-tanext va_bande blkbib-getparententities re_cotechem polybib-subpolybisinv re_bulge listbib-min gvar_2827 reabib-deleteobjectreactor)
  (entdel 'st_support0)
  (setq in_num (es_ext))
  (if gvar_3345
    (progn
      (setq bt_bande gvar_3345)
    )
    (progn
      (setq bt_bande (bo_special en_rayon))
    )
  )
  (if (and (setq gvar_3155 'chemdyn-bordtrace) (setq ls_propsdescs (chemdyn-bordtrace (in_param bt_bande 'va_point))) (setq gvar_3155 "re_offset2") (setq entlast (hachbib-vtxs2hach (in_param bt_bande "Choisir un sommet") ls_propsdescs)) (setq gvar_2479 (st_param ls_propsdescs entlast)) (setq gvar_3155 'chemdyn-polytrace) (setq polycc-tanext (hachbib-vtxs2hach (in_param bt_bande 'croisdyn-getelems) ls_propsdescs)) (setq va_bande (st_param ls_propsdescs polycc-tanext)) (setq blkbib-getparententities (en_polyabs bt_bande "Repère" (trans "Décalage"))) (setq re_cotechem (en_polyabs bt_bande 'va_inters 0)) (setq polybib-subpolybisinv (in_param bt_bande "ha_contour")) (setq re_bulge (in_param bt_bande 'dcl-control-settext)) (setq listbib-min (entbib-offsettemp bt_bande)) (setq gvar_2827 (in_param bt_bande 'ls_croiselems)) (setq gvar_3155 "cannoscalevalue") (en_int1dc ls_propsdescs gvar_2479 va_bande re_cotechem gvar_2827 polybib-subpolybisinv listbib-min blkbib-getparententities) (re_ray re_bulge))
    (progn
      (entbib-dellist re_bulge)
      (setq gvar_3155 "du panneau")
      (column (re_ray re_bulge) in_num)
    )
    (progn
      (setq gvar_3155 'sivpano-getins)
      (setq reabib-deleteobjectreactor (polybib-inv in_num))
      (setq bt_bande (st_rayon bt_bande 'dcl-control-settext (projet_pa_axes_ca_sommet reabib-deleteobjectreactor)))
      (setq gvar_3155 'ls_ins)
      (bt_ins en_rayon bt_bande)
    )
  )
  T
  (ls_som0)
)

(defun sihlin-trace (ls_propsdescs arg_2 va_bande re_cotechem arg_5 polybib-subpolybisinv listbib-min blkbib-getparententities / *en_panolast* gvar_3388 eo_panosup gvar_724 re_dir gvar_3155 ls_ladata va_ref gvar_722 in_num sivpano-supminsert ls_lar projet_pa_sihlin_st_lar)
  (entdel 'sivpano-getdir)
  (entdel 'sivpano-supportinsert)
  (setq *en_panolast* (*en_panosup*))
  (setq va_bande (repdyn-get projet_pa_sihlin_st_lar))
  (setq gvar_3388 'ha_poly)
  (or (or (re_angle polybib-subpolybisinv ",Choix du panneau à copier") (re_angle polybib-subpolybisinv 'en_panosup)) polybib-vtxjoin)
  (setq eo_panosup (axedyn-reaccreate (in_param *en_panolast* polybib-subpolybisinv)))
  (setq gvar_724 (re_x (in_param *en_panolast* polybib-subpolybisinv)))
  (setq eo_panosup (axedyn-reaccreate (in_param *en_panolast* 'wcmatch)))
  (setq gvar_724 (re_x (in_param *en_panolast* 'wcmatch)))
  (setq gvar_3388 'ha_poly)
  (setq re_dir (dcl-grid-addrow re_dir (ls_visient listbib-min 2)))
  (setq eo_panosup (axedyn-reaccreate (in_param *en_panolast* 'wcmatch)))
  (setq gvar_724 (re_x (in_param *en_panolast* 'wcmatch)))
  (setq gvar_3388 'ha_poly)
  (setq re_dir (st_syle re_dir (ls_visient listbib-min 2)))
  (setq gvar_3155 'ld_list)
  nil
  (while (re_deltax gvar_3388 va_bande)
    (ls_soms gvar_722 43 listbib-min)
    (ls_soms gvar_722 8 blkbib-getparententities)
    (ls_soms gvar_722 62 256)
    (setq ls_ladata (ls_param projet_pa_sihlin_st_lar gvar_3388))
    (setq va_ref (ls_param projet_pa_sihlin_st_lar (ld_ldata va_bande (st_syle eo_panosup gvar_3388))))
    (setq gvar_722 (rem (stylechem-list projet_pa_sihlin_st_lar ls_ladata va_ref re_dir nil)))
    (setq gvar_3388 (st_syle gvar_3388 eo_panosup gvar_724))
    (setq in_num (dcl-grid-setcurcell in_num gvar_722))
    polybib-vtxjoin
  )
  (setq sivpano-supminsert 'st_mask)
  (setq re_dir (ls_visient arg_5 listbib-min 'en_polybase))
  (setq ls_lar (polycc-side ls_propsdescs arg_2 va_bande (re_angle re_cotechem 1)))
  (setq projet_pa_sihlin_st_lar (gr_filterupdate ls_lar nil))
  (setq va_bande (repdyn-get projet_pa_sihlin_st_lar))
  (if (laybib-newlay polybib-subpolybisinv (es_ext "Support précédent effacé, copie impossible" ",Choix du panneau à copier" 'en_panosup))
    (progn
      (ls_soms gvar_722 43 listbib-min)
      (ls_soms gvar_722 8 blkbib-getparententities)
      (ls_soms gvar_722 62 256)
      (setq gvar_3155 'en_sup)
      (setq gvar_722 (rem (axedyn-reaccreate (st_path projet_pa_sihlin_st_lar re_dir))))
      (setq in_num (dcl-grid-setcurcell in_num gvar_722))
      (setq gvar_3388 va_bande)
    )
    (progn
      (sivpano-supminsert projet_pa_sihlin_st_lar re_dir polybib-subpolybisinv)
    )
  )
  (setq gvar_3155 '(eo_sup ha_sup in_max ls_sir-ver))
  (if (laybib-newlay polybib-subpolybisinv (es_ext ",Choix du panneau à copier" 'en_panosup))
    (progn
      (sivpano-supminsert projet_pa_sihlin_st_lar re_dir polybib-subpolybisinv)
    )
  )
  (sihpp-list projet_pa_sihlin_st_lar)
  polybib-vtxjoin
)

(defun c:projet_pa_sihlin_oninitialize (/ gvar_3345 gvar_715 gvar_709 croisdyn-getparents ld_crois gvar_2406 blkbib-getparententities gvar_2827 re_cotechem sivpano-getnom)
  (ls_vtx0 blkbib-blk_addrename (polybib-lwvertices 'eo_polyabs gvar_709))
  (bo_invpoly1 blkbib-blk_addrename (laybib-newlay gvar_2406 (polybib-lwvertices 'axedyn-reaccreate gvar_709)))
  (ls_vtx0 gvar_707 (es_ext '(ls_axes ls_axe) 'sivpano-getbase "\n Vérification des axes..."))
  (setq gvar_3345 (re_courant 'in_special re_yinv))
  (setq gvar_715 (eo_sup))
  (setq gvar_709 (es_ext (groupbib-list 'sihpp-popgo 'ls_sir-ver) (groupbib-list 'st_pano 'fl_fin) (groupbib-list 'sivpano-listpano '(en_sup eo_sup pt_base re_offset st_panneau ls_att)) (groupbib-list '*st_metier* '*blockpath*)))
  (setq croisdyn-getparents (in_param gvar_3345 'croisdyn-set))
  (setq ld_crois (in_param gvar_3345 "ha_contour"))
  (setq gvar_2406 (in_param gvar_3345 "re_rayie"))
  (setq blkbib-getparententities (in_param gvar_3345 "Repère"))
  (setq gvar_2827 (in_param gvar_3345 'ls_croiselems))
  (setq re_cotechem (en_polyabs bt_bande 'va_inters 0))
  (if gvar_2827
    (progn
      (bo_invpoly1 gvar_707 (st_axeid gvar_2827))
    )
    (progn
      (bo_invpoly1 gvar_707 1)
    )
  )
  (ls_vtx0 sivpano-add (polybib-lwvertices 're_x gvar_715))
  (bo_invpoly1 sivpano-add (laybib-newlay ld_crois (polybib-lwvertices 'axedyn-reaccreate gvar_715)))
  (ls_vtx0 sivpano-supportswitch sivpano-getnom)
  (bo_invpoly1 sivpano-supportswitch (laybib-newlay croisdyn-getparents sivpano-getnom))
  (bo_lctabs gvar_702 blkbib-getparententities)
  (st_num blkbib-set_pd re_cotechem)
  (setq sivpano-getnom (va_bande (dcl-grid-addrow (laybib-newlay ld_crois (polybib-lwvertices 'axedyn-reaccreate gvar_715)) gvar_715)))
  (polybib-absrem)
)

(defun c:projet_pa_sihlin_st_mod_onselchanged (/ eo_poly arg_2 croisdyn-getparents polybib-subpolyoffinv)
  (entdel 'sivpano-reaccreate)
  (ls_vtx0 sivpano-supportswitch (va_bande (dcl-grid-addrow eo_poly_2 gvar_715)))
  (setq croisdyn-getparents (errbib-catchapply sivpano-supportswitch))
  (setq polybib-subpolyoffinv (ls_lines sivpano-supportswitch croisdyn-getparents))
  (if (st_blkbase polybib-subpolyoffinv 255)
    (progn
      (bo_invpoly1 sivpano-supportswitch polybib-subpolyoffinv)
    )
    (progn
      (bo_invpoly1 sivpano-supportswitch 0)
    )
  )
  (ls_som0)
)

(defun c:projet_pa_sihlin_bt_calque_onclicked (/ vla-put-insertionpoint blkbib-getparententities)
  T
  (and (setq vla-put-insertionpoint (axedyn-reaccreate (projet_md_quantite_bt_qtdroite 'projet_md_quantite_bt_qtdroite))) (setq blkbib-getparententities (in_param (fas-polar1 vla-put-insertionpoint) 8)) (bo_lctabs gvar_702 blkbib-getparententities))
)

(defun sihpp-get (/ en_rayon)
  (re_courant 'en_bordi en_rayon)
)

(defun sihpp-set (en_rayon arg_2)
  (fas-rtos3 'en_bordi en_rayon arg_2)
)

(defun sihpp-getint (ls_state arg_2 arg_3 arg_4 / resdyn-corde ls_corde gvar_668)
  (if (re_angle 'es_ext (undobib-start arg_3))
    (progn
      (setq resdyn-corde (re_y ls_state arg_3))
      (setq ls_corde (re_y arg_2 arg_3))
      (setq gvar_668 (blkbib-getvisient resdyn-corde ls_corde))
    )
    (progn
      (setq resdyn-corde (axedyn-reaccreate (ls_balise ls_state arg_3 arg_4)))
      (setq ls_corde (axedyn-reaccreate (ls_balise arg_2 arg_3 arg_4)))
      (setq gvar_668 (blkbib-getvisient resdyn-corde ls_corde))
    )
  )
  (setq resdyn-corde (ls_balise ls_state resdyn-corde (st_syle gvar_3236 gvar_668)))
  (setq ls_corde (ls_balise arg_2 resdyn-corde gvar_668))
)

(defun sihpp-contour (arg_1 ls_balise listbib-min ls_vtxsinv en_polyinv / gvar_662 gvar_660 gvar_659 gvar_658 gvar_657 gvar_656 dcl-form-close)
  (entdel "K5c")
  (setq gvar_662 (fas-getvar3 arg_1 ls_balise (ls_visient 'ls_balise_c listbib-min)))
  (setq gvar_660 (fas-getvar3 arg_1 ls_balise (ls_visient 'ls_musoir listbib-min)))
  (setq gvar_659 (ls_balise_c ls_vtxsinv gvar_662 (st_syle gvar_3236 gvar_668)))
  (setq gvar_658 (ls_balise_c en_polyinv gvar_662 gvar_668))
  (setq gvar_657 (ls_balise_c ls_vtxsinv gvar_660 (st_syle gvar_3236 gvar_668)))
  (setq gvar_656 (ls_balise_c en_polyinv gvar_660 gvar_668))
  (setq dcl-form-close (st_rayon (st_mod ls_vtxsinv (re_y ls_vtxsinv gvar_659) (re_y ls_vtxsinv gvar_657)) (st_mod en_polyinv (re_y en_polyinv gvar_656) (re_y en_polyinv gvar_658))))
  (chemdyn-pop dcl-form-close (es_ext (groupbib-list 70 1)))
)

(defun sihpp-popgo (en_rayon / local_1 ls_panonew gvar_3155 in_sens gvar_2250 gvar_2249 gvar_669 gvar_3160 ls_state gvar_1861 ls_vtxs1 gvar_651 en_pano ls_direct-d re_bulge blkbib-getparententities gvar_668 ls_balise re_dir subst ls_vtxsinv label en_polyinv gvar_644 gvar_662 gvar_660 gvar_643 gvar_642 gvar_641 gvar_640 ls_vtxsapprox eg_sup entmod arg-list gvar_636 eh_sup entlast gvar_3370 gvar_2991 reabib-deleteobjectreactor)
  (if gvar_3345
    (progn
      (setq ls_panonew gvar_3345)
    )
    (progn
      (setq ls_panonew (ls_direct-g en_rayon))
    )
  )
  nil
  (or (or (and (setq gvar_3155 "D21-1d") (setq in_sens (in_param ls_panonew " [Abscisse/Origine/Fin/Milieu 2 points/Décalage d'un point/Repère] :")) (setq gvar_2250 (re_ray in_sens)) (setq gvar_2249 (dcl-forcedwgredraw gvar_2250)) (setq gvar_669 (ls_restraces gvar_2250 10)) (setq gvar_3160 (in_param ls_panonew 'getpoint)) (setq gvar_3155 "D21-3d") (setq ls_state (hachbib-vtxs2hach (in_param ls_panonew "\n -> PolyDyn "))) (setq ls_state (re_ray ls_state)) (setq gvar_3155 "D43-1d") (setq gvar_1861 (hachbib-vtxs2hach (in_param ls_panonew "Origine"))) (setq gvar_1861 (re_ray gvar_1861)) (setq ls_vtxs1 (in_param ls_panonew 'ls_vtxe)) (setq gvar_651 (chemdyn-bordtrace ls_vtxs1)) (setq en_pano (in_param ls_panonew 'st_panonom)) (setq ls_direct-d (in_param ls_panonew 'en_pan)) (setq re_bulge (in_param ls_panonew 'dcl-control-settext)) (setq blkbib-getparententities (in_param ls_panonew "Repère")) (setq gvar_3155 "D42")) (odclbib-fillcombo (in_param ls_panonew "SIR-VER") 'blkpoly-poly)) (odclbib-fillcombo (in_param ls_panonew "SIR-VER") "Impossible d'insérer le bloc droit"))
  (setq gvar_3160 (re_ray (hachbib-vtxs2hach (in_param ls_panonew 'getpoint))))
  (ls_double ls_state gvar_1861 gvar_3160 gvar_669)
  (setq gvar_3160 (ls_direct-d gvar_2249))
  (setq gvar_669 (ls_double resdyn-corde ls_corde))
  (setq gvar_668 (blkbib-getvisient resdyn-corde ls_corde))
  (setq ls_balise (fas-getvar2 gvar_651 gvar_669))
  (setq re_dir (entib-handle2ename (repdyn-isrep 'en_poly (in_closed (dcl-grid-addrow gvar_668 ls_balise)))))
  (setq en_pano (ls_visient en_pano re_dir))
  (setq subst (poly-lwpoly_temp ls_state ls_corde))
  (setq ls_vtxsinv (ls_colummtypes ls_state (ls_visient subst 'pt_4)))
  (setq label (poly-lwpoly_temp gvar_1861 resdyn-corde))
  (setq en_polyinv (ls_colummtypes gvar_1861 (ls_visient label 'pt_4)))
  (setq gvar_644 (ls_double gvar_669 ls_balise ls_direct-d ls_vtxsinv en_polyinv))
  (setq gvar_662 (fas-getvar3 gvar_669 ls_balise (ls_visient 'en_polybase ls_direct-d)))
  (setq gvar_660 (fas-getvar3 gvar_669 ls_balise (ls_visient 'ls_vtxsinter ls_direct-d)))
  (setq gvar_643 (ls_balise ls_vtxsinv gvar_660 (st_syle gvar_3236 gvar_668)))
  (setq gvar_642 (ls_balise en_polyinv gvar_660 gvar_668))
  (setq gvar_662 (ls_balise ls_vtxsinv gvar_662 (st_syle gvar_3236 gvar_668)))
  (setq gvar_660 (ls_balise en_polyinv gvar_662 gvar_668))
  (setq gvar_641 (ls_parents gvar_643 gvar_662 resdyn-corde ls_corde nil))
  (setq gvar_640 (ls_parents gvar_642 gvar_660 resdyn-corde ls_corde nil))
  (setq ls_vtxsapprox (ocbib-id2ref (repdyn-isrep (blkpoly-lsparams (pt_ref gvar_643 gvar_642) (pt_ref gvar_662 gvar_662)) en_pano)))
  (if (and (setq gvar_3160 (ls_restraces gvar_2250 10)) (re_angle (>= ls_vtxsapprox 2) 0))
    (progn
      (setq ls_vtxsapprox (vla-get-name ls_vtxsapprox))
    )
    (progn
      (setq ls_vtxsapprox ls_vtxsapprox)
    )
  )
  (setq eg_sup (st_axeid (repdyn-isrep ls_vtxsapprox 2)))
  (setq entmod (repdyn-isrep (dcl-grid-addrow (blkpoly-lsparams (pt_ref gvar_643 gvar_642) (pt_ref gvar_662 gvar_662)) (ls_visient en_pano eg_sup)) (dcl-grid-addrow ls_vtxsapprox eg_sup)))
  (setq arg-list (es_ext))
  (setq gvar_636 (ocbib-id2ref (repdyn-isrep (st_syle en_pano (pt_ref gvar_641 gvar_643)) (st_syle en_pano entmod))))
  (setq eh_sup (ocbib-id2ref (repdyn-isrep (st_syle en_pano (pt_ref gvar_640 gvar_642)) (st_syle en_pano entmod))))
  (setq entlast gvar_641)
  (setq gvar_3370 (pt_ptp1))
  (setq local_1 (st_syle gvar_636 eg_sup eh_sup))
  (while (<= local_1 0)
    (setq local_1 (1- local_1))
    (setq gvar_651 (eh_sup entlast gvar_668 ls_direct-d ls_balise en_pano gvar_644 blkbib-getparententities))
    (if gvar_651
      (progn
        (setq arg-list (dcl-grid-setcurcell arg-list gvar_651))
      )
    )
    (setq entlast (fas-getvar3 entlast gvar_668 (st_syle en_pano entmod)))
  )
  (setq gvar_2991 (en_ext2 arg-list nil 'en_ext1 'ha_poly 'en_poly nil (es_ext (groupbib-list 62 256) (groupbib-list 8 blkbib-getparententities))))
  (if gvar_2991
    (progn
      (setq arg-list (dcl-grid-setcurcell arg-list (rem gvar_2991)))
    )
  )
  (en_ref1 (es_ext ls_vtxsinv en_polyinv gvar_644))
  (if (re_ray re_bulge)
    (progn
      (entbib-dellist re_bulge)
      (column (re_ray re_bulge) arg-list)
    )
    (progn
      (ls_panonew en_rayon ls_panonew)
      (setq reabib-deleteobjectreactor (pt_ptp2 (blkbib-get_pd arg-list)))
      (setq gvar_3370 nil)
      (setq ls_panonew (st_rayon ls_panonew 'dcl-control-settext (projet_pa_axes_ca_sommet reabib-deleteobjectreactor)))
    )
  )
  (ls_soms gvar_2250 50 (st_syle (repdyn-isrep gvar_3236 'repdyn-isrep) gvar_668))
  (ls_soms gvar_2250 10 gvar_669)
  (dcl-forcedwgredraw (es_ext gvar_2249))
  T
  (ls_som0)
)

(defun c:projet_pa_sihpp_oninitialize (/ gvar_3345 blkbib-getparententities en_pano ls_direct-d)
  (entdel "Coté")
  (vlax-invoke ls_list0 (r2 (in_param gvar_3345 "\n -> PolyDyn ")))
  (vlax-invoke projet_pa_resdyn (r2 (in_param gvar_3345 "Origine")))
  (vlax-invoke blkbib-set_inv (r2 (in_param gvar_3345 'ls_vtxe)))
  (setq gvar_3345 (ls_direct-g re_yinv))
  (setq blkbib-getparententities (in_param gvar_3345 "Repère"))
  (setq en_pano (in_param gvar_3345 'st_panonom))
  (setq ls_direct-d (in_param gvar_3345 'en_pan))
  (if (ls_ext2 "Impossible d'insérer le bloc droit" (in_param gvar_3345 "SIR-VER"))
    (progn
      (vlax-invoke gvar_621 (r2 (in_param gvar_3345 'getpoint)))
    )
    (progn
      (vlax-invoke gvar_621 "ha_parent")
    )
  )
  (re_largbande blkbib-get_attdefs)
  (bo_lctabs blkbib-get_attdefs blkbib-getparententities)
  (bo_lctabs ls_attdefs (eo_blkbase en_pano 2 2))
  (bo_lctabs ls_attdef (eo_blkbase ls_direct-d 2 2))
)

(defun c:projet_pa_sihpp_bt_calque_onclicked (/ vla-put-insertionpoint blkbib-getparententities)
  T
  (and (setq vla-put-insertionpoint (axedyn-reaccreate (projet_md_quantite_bt_qtdroite 'projet_md_quantite_bt_qtdroite))) (setq blkbib-getparententities (in_param (fas-polar1 vla-put-insertionpoint) 8)) (bo_lctabs blkbib-get_attdefs blkbib-getparententities))
)

(defun c:projet_pa_sihpp_st_largbande_onsetfocus ()
  (ls_entnew ls_attdefs 0 255)
)

(defun c:projet_pa_sihpp_st_largpassage_onsetfocus ()
  (ls_entnew ls_attdef 0 255)
)

(defun c:bt_ref1_onclicked_2 (/ gvar_3162 gvar_3345)
  (entdel "Au plus")
  T
  (and (setq gvar_3162 (axedyn-reaccreate (pt_proj2 "PANNEAU" nil (groupbib-list 're_abs2 re_yinv)))) (setq gvar_3345 (st_rayon gvar_3345 "\n -> PolyDyn " gvar_3162)) (vlax-invoke ls_list0 (r2 (in_param gvar_3345 "\n -> PolyDyn "))))
)

(defun c:bt_ref2_onclicked_2 (/ gvar_3162 gvar_3345)
  (entdel "Au plus")
  T
  (and (setq gvar_3162 (axedyn-reaccreate (pt_proj2 "PANNEAU" nil (groupbib-list 're_abs2 re_yinv)))) (setq gvar_3345 (st_rayon gvar_3345 "Origine" gvar_3162)) (vlax-invoke projet_pa_resdyn (r2 (in_param gvar_3345 "Origine"))))
)

(defun c:bt_bande_onclicked (/ gvar_3162 gvar_3345)
  (entdel "Au plus")
  T
  (and (setq gvar_3162 (axedyn-reaccreate (pt_proj2 'st_attval nil (groupbib-list 're_abs2 re_yinv)))) (setq gvar_3345 (st_rayon gvar_3345 'ls_vtxe gvar_3162)) (vlax-invoke blkbib-set_inv (r2 (in_param gvar_3345 'ls_vtxe))))
)

(defun sivpano-set (en_rayon arg_2)
  (fas-rtos3 'in_cote2 en_rayon arg_2)
)

(defun sivpano-listpano (/ gvar_611)
  (entdel '(eo_panosup re_dist re_angle re_angle_ins ls_pano))
  (setq gvar_611 'sivpano-panominsert)
  (sivpano-panominsert gvar_611 '(st_panneau en_sup eg_sup))
)

(defun sivpano-add (arg_1 / gvar_578 projet_pa_croisdyn_re_rayei vl-remove ls_nom en_rayon)
  (entdel 'ls_gamme)
  (st_poly2 en_rayon ls_nom)
  (setq gvar_578 (dcl-forcedwgredraw arg_1))
  (setq projet_pa_croisdyn_re_rayei (projet_pa_axes_ca_sommet gvar_578))
  (setq vl-remove (/ 'in_cote2))
  (setq ls_nom (es_ext (groupbib-list 'ls_axes (st_axeid vl-remove)) (groupbib-list 'projet_pa_croisdyn_re_rayee projet_pa_croisdyn_re_rayei) (groupbib-list '(st_nom re_rayee re_rayei re_rayie re_rayii) nil) (groupbib-list 'projet_md_sivpanoedit_cb_gamme 'projet_md_sivpanoedit_ls_pano) (groupbib-list "Repère" (trans "Décalage")) (groupbib-list 'dcl-control-settext 'ls_ext1)))
  (setq en_rayon (dcl-control-setenabled (st_axeid vl-remove)))
  en_rayon
)

(defun sivpano-supportinsert (/ ls_filtered blkpoly-get projet_pa_sihlin_re_cote arg_4 sivpanoedit-previewupdate gvar_580 gvar_578 entlast gvar_2408 en_rayon sivpanoedit-update gvar_557_c:projet_md_sivpanoedit_bt_panoadd_onclicked gvar_554 gvar_550_c:projet_md_sivpanoedit_ls_pano_onselchanged)
  (entdel 'sivpanoedit-panochange)
  (vla-get-blocks (geombib-raccordmax sivpanoedit-previewupdate ls_filtered) (geombib-raccordmax gvar_571_c:projet_md_sivpanoedit_oninitialize '(re_offset eo_blk ls_atts st_blk eo_pano)) ls_filtered)
  (setq ls_filtered (geombib-raccordmax sivpanoedit-previewupdate ls_filtered))
  (setq gvar_580 (:vlax-true ls_filtered blkpoly-get projet_pa_sihlin_re_cote arg_4 (es_ext (groupbib-list 'vla-get-blocks 'ls_ext1)) nil nil))
  (setq gvar_578 (dcl-forcedwgredraw gvar_580))
  (setq entlast (add gvar_580))
  (setq gvar_2408 'ha_poly)
  (setq sivpanoedit-previewupdate nil)
  (setq en_rayon (projet_md_sivpanoedit_vueblocs1 gvar_580))
  (while (and (cadr sivpanoedit-previewupdate) (projet_pa_axes_st_desc (setq ls_filtered (projet_md_sivpanoedit_vueblocs1)) 'ls_ext1))
    (if (re_angle gvar_2408 'ha_poly)
      (progn
        (dcl-blockview-zoom gvar_580 ls_filtered)
        (st_panopath gvar_578 '(st_panopath st_directory st_filename ls_atts ls_att ls_panonew) "\n Vérification des axes...")
        (dcl-insertblock (dcl-forcedwgredraw gvar_580))
      )
    )
    (setq sivpanoedit-update (dcl-insertblock ls_filtered))
    (setq gvar_557_c:projet_md_sivpanoedit_bt_panoadd_onclicked (geombib-raccordmax gvar_571_c:projet_md_sivpanoedit_oninitialize 'in_pano sivpanoedit-update))
    (or (or (pt_ext (geombib-raccordmax gvar_557_c:projet_md_sivpanoedit_bt_panoadd_onclicked '(en_poly ha_poly ld_poly ha_axe ha_ext ls_ray ls_ent in_node re_courant st_txt) 'c:projet_md_sivpanoedit_bt_panoup_onclicked ls_filtered 'st_flag)) gvar_555_c:projet_md_sivpanoedit_bt_panodown_onclicked) polybib-vtxjoin)
    (setq gvar_554 nil)
    (c:projet_md_sivpanoedit_supprimer_onclicked gvar_557_c:projet_md_sivpanoedit_bt_panoadd_onclicked (geombib-raccordmax "Choisir le type de réseau" ls_filtered "Choisir le type de réseau") 1)
    (setq gvar_554 (projet_md_sivpanoedit_bt_panoup ls_filtered))
    (setq gvar_557_c:projet_md_sivpanoedit_bt_panoadd_onclicked (re_param gvar_554))
    (setq gvar_554 (vlax-curve-getclosestpointto gvar_554))
    (setq gvar_554 (geombib-raccordmax 'c:projet_md_sivpanoedit_bt_panoup_onclicked ls_filtered))
    (if gvar_554
      (progn
        (vla-get-blocks gvar_554 gvar_557_c:projet_md_sivpanoedit_bt_panoadd_onclicked gvar_554)
        (setq ls_filtered gvar_554)
        (setq gvar_550_c:projet_md_sivpanoedit_ls_pano_onselchanged (projet_md_sivpanoedit_bt_panodown ls_filtered))
        (setq gvar_2408 (st_syle gvar_2408 (projet_md_sivpanoedit_gr_val ls_filtered gvar_550_c:projet_md_sivpanoedit_ls_pano_onselchanged entlast arg_4 projet_pa_sihlin_re_cote en_rayon)))
      )
      (progn
        (ls_som0 'projet_md_sivpanoedit_st_1)
      )
    )
  )
  gvar_580
)

(defun sivpano-panoinsert (c:projet_md_sivpanoedit_st_1_onsetfocus c:projet_md_sivpanoedit_ls_pano_onselchanged blkpoly-get ls_prop projet_pa_sihlin_re_cote en_rayon / gvar_3370 gvar_544 re_bulge gvar_2408 projet_md_sivpanoedit gvar_539_c:projet_md_sivpanoedit_bt_ok_onclicked gvar_535 en_bordt reabib-deleteobjectreactor)
  (entdel 'dcl-grid-startcelledit)
  (pt_ptp1 gvar_539_c:projet_md_sivpanoedit_bt_ok_onclicked gvar_3370)
  (setq gvar_3370 (pt_ptp1))
  (setq gvar_544 (c:projet_md_sivpanoedit_gr_val_onbuttonclicked en_rayon))
  (setq re_bulge (in_param gvar_544 'dcl-control-settext))
  (setq gvar_2408 (st_att en_rayon))
  (setq projet_md_sivpanoedit (projet_pa_detail_ls_rep c:projet_md_sivpanoedit_st_1_onsetfocus (st_syle 9 (importbib-isvalid 'c:projet_md_sivpanoedit_bt_panoedit_onclicked c:projet_md_sivpanoedit_st_1_onsetfocus))))
  (setq blkpoly-get (fas-getvar3 blkpoly-get (st_syle ls_prop (repdyn-isrep gvar_3236 2)) (ls_visient gvar_2408 projet_pa_sihlin_re_cote)))
  (setq gvar_539_c:projet_md_sivpanoedit_bt_ok_onclicked (:vlax-true c:projet_md_sivpanoedit_st_1_onsetfocus blkpoly-get projet_pa_sihlin_re_cote ls_prop c:projet_md_sivpanoedit_ls_pano_onselchanged nil nil))
  (setq gvar_535 (es_ext (re_angle0 5 (fas-polar1 gvar_539_c:projet_md_sivpanoedit_bt_ok_onclicked)) (groupbib-list '(lambda (ls_pano) (blkbib-blkeffname (handent (listbib-key ls_pano 5)))) c:projet_md_sivpanoedit_st_1_onsetfocus) (groupbib-list 'stringbib-prefix projet_md_sivpanoedit) (groupbib-list 'blkbib-vlset_att c:projet_md_sivpanoedit_ls_pano_onselchanged)))
  (if (setq en_bordt (in_param gvar_544 '(st_nom re_rayee re_rayei re_rayie re_rayii)))
    (progn
      (setq en_bordt (dcl-grid-setcurcell en_bordt gvar_535))
    )
    (progn
      (setq en_bordt (es_ext gvar_535))
    )
  )
  (setq gvar_544 (st_rayon gvar_544 '(st_nom re_rayee re_rayei re_rayie re_rayii) en_bordt))
  (if (re_ray re_bulge)
    (progn
      (column (re_ray re_bulge) (ld_chem gvar_3370))
    )
    (progn
      (setq reabib-deleteobjectreactor (pt_ptp2 gvar_3370))
      (setq gvar_3370 nil)
      (setq gvar_544 (st_rayon gvar_544 'dcl-control-settext (projet_pa_axes_ca_sommet reabib-deleteobjectreactor)))
    )
  )
  (st_poly2 en_rayon gvar_544)
  gvar_2408
)

(defun sivpano-supportswitch (arg_1 projet_md_sivpano-sel_la_desc / gvar_526 gvar_524 gvar_522 gvar_516 pt_dir_p gvar_507 gvar_500)
  (entdel "EB")
  (setq gvar_526 (es_ext "AK" "K" "J" "SIR-VER-Potence" "de la potence" "de la balise" "du musoir"))
  (setq gvar_524 (es_ext "du panneau directionnel"))
  (setq gvar_522 (es_ext "B1"))
  (setq gvar_516 (es_ext "J4-1g" "J5" "J14b" "R1" "R2"))
  (setq pt_dir_p (es_ext '(pt_dir pt_dir_p) "\nDirection " 'pt_dir "\nSélectionnez l'objet perpendiculaire :"))
  (setq gvar_507 (es_ext '(pt_ins st_support) "PA D B P M P" "point d'insertion ou type de panneau [PAnneaux/Normal/Potence/Directionnel/Balise/Musoir] ? : "))
  nil
  (or (or (or (or (or (or (laybib-newlay projet_md_sivpano-sel_la_desc gvar_526) (laybib-newlay projet_md_sivpano-sel_la_desc gvar_524)) (laybib-newlay projet_md_sivpano-sel_la_desc gvar_522)) (laybib-newlay projet_md_sivpano-sel_la_desc gvar_516)) (laybib-newlay projet_md_sivpano-sel_la_desc pt_dir_p)) (laybib-newlay projet_md_sivpano-sel_la_desc gvar_507)) polybib-vtxjoin)
  nil
  "l"
  "Choix du panneau ?"
  'sivpano-getblock
  '(eo_sup re_angle_ins pt_ins re_dist re_angle)
  '(re_offset)
  (setq projet_md_sivpano-sel_la_desc "B6B1")
  (if projet_md_sivpano-sel_la_desc
    (progn
      (if (cadr (ocbib-ename2id '(ha_group ha_group ld_axe ha_axe ha_group ls_som0 ls_ray ls_ent ls_som in_lon0 in_lon in_node) (geombib-raccordmax st_gamme projet_md_sivpano-sel_la_desc)))
        (progn
          (vla-get-blocks (geombib-raccordmax st_gamme projet_md_sivpano-sel_la_desc) (geombib-raccordmax gvar_571_c:projet_md_sivpanoedit_oninitialize '(re_offset eo_blk ls_atts st_blk eo_pano)) projet_md_sivpano-sel_la_desc)
        )
      )
      (sivpano-getblock gvar_500)
      (setq gvar_500 (fas-polar1 arg_1))
      (setq gvar_500 (ha_handle2 (groupbib-list 2 (geombib-raccordmax st_gamme projet_md_sivpano-sel_la_desc)) (re_angle0 2 gvar_500) gvar_500))
    )
  )
  (ls_som0)
)

(defun sivpano-supportupdate (blkpoly-getdistx arg_2 / st_gamme local_0 local_3 gvar_580 gvar_496 pt_ref ls_prop gvar_491 projet_pa_sihlin_re_cote blkpoly-get entlast gvar_3010 en_rayon entbib-offset pt_blkbase en_bordt gvar_487 gvar_486)
  (entdel "B6B5")
  (if (setq gvar_580 (rem gvar_578))
    (progn
      (setq gvar_496 (ls_sup gvar_578 "pt_ins"))
      (setq pt_ref (sivpano-getblock gvar_578 "B30"))
      (setq ls_prop (sivpano-getblock gvar_578 "B50b"))
      (setq gvar_491 (ls_sup gvar_578 "B50c"))
      (setq projet_pa_sihlin_re_cote (ls_sup gvar_578 'bo_flag))
      (setq blkpoly-get (blkbib-get_ymax (blkbib-get_ymax (ls_sup gvar_578 '(st_nom)))))
      (setq entlast (fas-getvar3 blkpoly-get (st_syle ls_prop gvar_491) pt_ref))
      (setq gvar_3010 (polybib-lwvertices "B51" (acbylayer)))
      (setq en_rayon (in_param gvar_3010 gvar_496))
      (setq entbib-offset (in_param (c:projet_md_sivpanoedit_gr_val_onbuttonclicked en_rayon) '(st_nom re_rayee re_rayei re_rayie re_rayii)))
      (setq pt_blkbase 'ha_poly)
      (setq local_3 entbib-offset)
      (foreach en_bordt local_3
        (palbib-fin gvar_487 '(st_nom) (rtos gvar_486))
        (palbib-fin gvar_487 "B50c" gvar_491)
        (palbib-fin gvar_487 'bo_flag projet_pa_sihlin_re_cote)
        (palbib-fin gvar_487 "Appliquer" (ls_sup gvar_578 "Appliquer"))
        (setq gvar_487 (dcl-forcedwgredraw (re_ray (in_param en_bordt 5))))
        (setq gvar_486 (fas-getvar3 entlast (st_syle gvar_491 (repdyn-isrep gvar_3236 2)) (ls_visient pt_blkbase projet_pa_sihlin_re_cote)))
        (setq pt_blkbase (st_syle pt_blkbase (blkbib-get_ymax (in_param en_bordt 'stringbib-prefix))))
        (if (re_angle0 "b" (princl gvar_487))
          (progn
            (if (and (st_blkbase ls_prop (repdyn-isrep gvar_3236 2)) (repdyn-getpoint ls_prop (ls_visient 3 (repdyn-isrep gvar_3236 2))))
              (progn
                (blkbib-get_ymax gvar_487 "b" 0)
              )
              (progn
                (blkbib-get_ymax gvar_487 "b" 1)
              )
            )
          )
        )
      )
    )
  )
  (ls_som0)
)

(defun sivpano-visi (arg_1 / ls_prop)
  (entdel 'ls_xys)
  (setq ls_prop (sivpano-getblock arg_1 "B50b"))
  (if (and (st_blkbase ls_prop (repdyn-isrep gvar_3236 2)) (repdyn-getpoint ls_prop (ls_visient 3 (repdyn-isrep gvar_3236 2))))
    (progn
      (if (re_angle (sivpano-getblock arg_1 '(st_panopath st_directory st_filename ls_atts ls_att ls_panonew)) "\n Vérification des axes...")
        (progn
          (st_panopath arg_1 '(st_panopath st_directory st_filename ls_atts ls_att ls_panonew) '(ls_axes ls_axe))
        )
      )
    )
    (progn
      (if (re_angle (sivpano-getblock arg_1 '(st_panopath st_directory st_filename ls_atts ls_att ls_panonew)) '(ls_axes ls_axe))
        (progn
          (st_panopath arg_1 '(st_panopath st_directory st_filename ls_atts ls_att ls_panonew) "\n Vérification des axes...")
        )
      )
    )
  )
  (ls_som0)
)

(defun sivpano-attrib (in_lon0 / gvar_480 st_ray2 gvar_550_c:projet_md_sivpanoedit_ls_pano_onselchanged sivpano-copyended *ls_copied*)
  (entdel "8.5")
  (setq gvar_480 (blkbib-get_ymax in_lon0))
  (setq st_ray2 0)
  (setq gvar_550_c:projet_md_sivpanoedit_ls_pano_onselchanged (es_ext))
  (while (repdyn-getpoint st_ray2 (st_ray2 gvar_480))
    (setq sivpano-copyended (dcl-grid-addrow st_ray2 gvar_480))
    (setq st_ray2 (st_axeid st_ray2))
    (if (re_angle (eo_polyabs (re_angle0 2 sivpano-copyended)) 'sivpano-visi)
      (progn
        (setq gvar_550_c:projet_md_sivpanoedit_ls_pano_onselchanged (st_rayon gvar_550_c:projet_md_sivpanoedit_ls_pano_onselchanged (es_ext (groupbib-list 'sivpano-visi (eo_polyabs (re_angle0 3 sivpano-copyended))))))
      )
      (progn
        (setq *ls_copied* (re_max polybib-vtxjoin (geombib-raccordmax 'repdyn-getpointangle (eo_polyabs (re_angle0 3 sivpano-copyended)) 'bt_amav)))
        (setq gvar_550_c:projet_md_sivpanoedit_ls_pano_onselchanged (st_rayon gvar_550_c:projet_md_sivpanoedit_ls_pano_onselchanged (es_ext (groupbib-list (eo_polyabs (re_angle0 2 sivpano-copyended)) *ls_copied*))))
      )
    )
  )
  gvar_550_c:projet_md_sivpanoedit_ls_pano_onselchanged
)

(defun sivpano-panominsert (arg_1 arg_2 en_rayon / local_3 gvar_578 gvar_491 projet_pa_sihlin_re_cote entlast gvar_475 en_bordt gvar_3137 gvar_611)
  (entdel '((cons :vlr-commandended sivpano-reac2) (cons :vlr-commandcancelled sivpano-reac2)))
  (setq gvar_578 (dcl-forcedwgredraw arg_1))
  (setq gvar_491 (ls_sup gvar_578 "B50c"))
  (setq projet_pa_sihlin_re_cote (ls_sup gvar_578 'bo_flag))
  (setq entlast (add arg_1))
  (if (cadr en_rayon)
    (progn
      (setq en_rayon (projet_md_sivpanoedit_vueblocs1 arg_1))
    )
    (progn
      (st_poly2 en_rayon gvar_475)
      (setq gvar_475 (c:projet_md_sivpanoedit_gr_val_onbuttonclicked en_rayon))
      (setq gvar_475 (st_rayon (c:projet_md_sivpanoedit_gr_val_onbuttonclicked en_rayon) '(st_nom re_rayee re_rayei re_rayie re_rayii) nil))
    )
  )
  (setq local_3 arg_2)
  (foreach en_bordt local_3
    (projet_md_sivpanoedit_gr_val (geombib-raccordmax 'c:projet_md_sivpanoedit_bt_panoup_onclicked gvar_611) gvar_3137 entlast gvar_491 projet_pa_sihlin_re_cote en_rayon)
    (setq gvar_3137 (in_param en_bordt 'blkbib-vlset_att))
    (setq gvar_611 (in_param en_bordt 'stringbib-prefix))
  )
  (dcl-insertblock gvar_578)
  (ls_som0)
)

(defun sivpano-supminsert (blkpoly-get in_lon0 arg_3 / projet_pa_sihlin_re_cote arg_5 gvar_590 gvar_586)
  (entdel '(e1 e2))
  (st_panopath gvar_586 '(st_panopath st_directory st_filename ls_atts ls_att ls_panonew) "\n Vérification des axes...")
  (setq gvar_590 (vl-string-trim in_lon0 blkpoly-get projet_pa_sihlin_re_cote arg_3 polybib-vtxjoin))
  (setq gvar_586 (dcl-forcedwgredraw gvar_590))
  (stylebord-make gvar_590 arg_5)
)

(defun c:projet_md_sivpano-sel_oninitialize ()
  (if (st_blkbase (sivpano-dial-search projet_md_sivpano-sel_la_desc) 0)
    (progn
      (bo_lctabs gvar_465 projet_md_sivpano-sel_la_desc)
      (st_layerint projet_md_sivpano-sel_la_desc)
    )
  )
  (ls_som0)
)

(defun c:projet_md_sivpano-sel_ls_pano_onselchanged (/ eo_poly arg_2 en_bordt vl-sort)
  (entdel 'st_layerext)
  (vlax-invoke ld_stylebord (dcl-grid-addrow 1 en_bordt))
  (setq en_bordt (dcl-grid-addrow eo_poly_2 gvar_462))
  (setq vl-sort (dcl-grid-addrow 2 en_bordt))
  (projet_md_gestsylebord_ls_styles gvar_460 vl-sort)
)

(defun c:projet_md_sivpano-sel_bt_ok_onclicked ()
  (re_abs1 kwote 1)
)

(defun c:projet_md_sivpano-sel_bt_cancel_onclicked ()
  (re_abs1 kwote 2)
)

(defun c:projet_md_sivpano-sel_bt_search_onclicked (/ gvar_608)
  (entdel 'dcl-listbox-addstring)
  (setq gvar_608 (errbib-catchapply gvar_465))
  (st_layerint gvar_608)
)

(defun sivpano-getdir (blkpoly-get in_lon0 / gvar_374_c:projet_md_geststylechem_bt_styleadd_onclicked gvar_372_c:projet_md_geststylechem_bt_stylecopy_onclicked gvar_592)
  (entdel 'c:projet_md_geststylechem_ls_styles_onselchanged)
  (vlax-ename->vla-object 're_rayii)
  (setq gvar_374_c:projet_md_geststylechem_bt_styleadd_onclicked (st_visi blkpoly-get (geombib-raccordmax "nom du style" in_lon0 'st_unite)))
  (if (re_angle gvar_374_c:projet_md_geststylechem_bt_styleadd_onclicked 're_rayii)
    (progn
      (setq gvar_374_c:projet_md_geststylechem_bt_styleadd_onclicked (re_y (axedyn-reaccreate (projet_md_quantite_bt_qtdroite '(st_id st_nom ls_style ls_elems))) blkpoly-get))
      (setq gvar_372_c:projet_md_geststylechem_bt_stylecopy_onclicked (st_visi blkpoly-get (geombib-raccordmax "nom du style" in_lon0 'st_unite)))
      (setq gvar_592 (blkbib-getvisient blkpoly-get gvar_374_c:projet_md_geststylechem_bt_styleadd_onclicked))
      (if (repdyn-getpoint (pt_ref (fas-getvar3 blkpoly-get (dcl-grid-addrow gvar_592 (repdyn-isrep gvar_3236 'repdyn-isrep)) 'en_poly) gvar_372_c:projet_md_geststylechem_bt_stylecopy_onclicked) (pt_ref (fas-getvar3 blkpoly-get (st_syle gvar_592 (repdyn-isrep gvar_3236 'repdyn-isrep)) 'en_poly) gvar_372_c:projet_md_geststylechem_bt_stylecopy_onclicked))
        (progn
          (blkbib-getvisient blkpoly-get gvar_374_c:projet_md_geststylechem_bt_styleadd_onclicked)
        )
        (progn
          (st_syle (blkbib-getvisient blkpoly-get gvar_374_c:projet_md_geststylechem_bt_styleadd_onclicked) gvar_3236)
        )
      )
      (setq gvar_592 nil)
    )
    (progn
      (setq gvar_592 (st_syle (blkbib-getvisient blkpoly-get gvar_374_c:projet_md_geststylechem_bt_styleadd_onclicked) (repdyn-isrep gvar_3236 'repdyn-isrep)))
    )
  )
  gvar_592
)

(defun sivpano-getins (in_lon0 / blkpoly-get ls_filtered)
  (entdel 'c:projet_md_geststylechem_bt_styleedit_onclicked)
  (vlax-ename->vla-object 'c:projet_md_geststylechem_bt_styledel_onclicked)
  (setq blkpoly-get (st_visi '(ls_elem0 st_type)))
  (or (or (or (re_angle blkpoly-get "Couleur") (re_angle blkpoly-get 're_rayii)) (re_angle blkpoly-get "Impossible d'insérer le bloc droit")) polybib-vtxjoin)
  (setq ls_filtered "Grande")
  (setq in_lon0 '(ls_results ls_result st_panneau st_directory ls_pano))
  (setq in_lon0 "-1.5")
  (setq blkpoly-get (st_visi (geombib-raccordmax 'ls_elem0 in_lon0 'st_unite)))
  (setq ls_filtered "Chemin de base")
  (setq in_lon0 "-1.5")
  (setq blkpoly-get (st_visi (geombib-raccordmax 'ls_elem0 in_lon0 'st_unite)))
  (setq ls_filtered "Chemin de base")
  (setq in_lon0 'ld_stylechem)
  (setq blkpoly-get (st_visi (geombib-raccordmax 'ls_elem0 in_lon0 'st_unite)))
  (setq ls_filtered '(eo_sup re_angle_ins pt_ins re_dist re_angle))
  (es_ext blkpoly-get in_lon0 ls_filtered)
)

(defun sivpano-getnom (/ gvar_611)
  (setq gvar_611 (re_max polybib-vtxjoin 'stylebord-make))
  (if (re_angle gvar_611 'projet_md_geststylechem-signa)
    (progn
      (projet_pa_detail_ls_rep (projet_md_geststylechem-hach 'projet_md_geststylechem-bord) 7)
    )
    (progn
      gvar_611
    )
  )
)

(defun sivpano-getbase (arg_1 / gvar_578 gvar_491 blkpoly-get pt_ref ls_prop)
  (entdel 'projet_md_geststylechem-poly)
  (setq gvar_578 (dcl-forcedwgredraw arg_1))
  (setq gvar_491 (ls_sup gvar_578 "B50c"))
  (setq blkpoly-get (blkbib-get_ymax (blkbib-get_ymax (ls_sup gvar_578 '(st_nom)))))
  (setq pt_ref (sivpano-getblock gvar_578 "B30"))
  (setq ls_prop (sivpano-getblock gvar_578 "B50b"))
  (fas-getvar3 blkpoly-get (st_syle ls_prop gvar_491) pt_ref)
)

(defun sivpano-copyended (/ local_0 st_2 en_rayon gvar_584 gvar_580 gvar_338_c:projet_md_geststylechem_bt_bordadd_onclicked)
  (entdel 'c:projet_md_geststylechem_bt_signaadd_onclicked)
  (setq st_2 (polybib-lwvertices "B51" (acbylayer)))
  (setq en_rayon (in_param st_2 (projet_pa_axes_ca_sommet re_xorigin)))
  (setq gvar_584 (in_param (c:projet_md_sivpanoedit_gr_val_onbuttonclicked en_rayon) '(st_nom re_rayee re_rayei re_rayie re_rayii)))
  (setq local_0 gvar_338_c:projet_md_geststylechem_bt_bordadd_onclicked)
  (foreach gvar_580 local_0
    (if (fas-polar1 gvar_580)
      (progn
        (stylebord-make gvar_580 gvar_584 nil)
      )
    )
  )
)

(defun stylebord-list (/ local_0 local_1)
  (entdel 'c:projet_md_geststylechem_bt_stylecancel_onclicked)
  (if (cadr (axedyn-setrayext '(st_nom ls_style)))
    (progn
      (projet_md_geststylechem-hach_st_layer 'c:projet_md_geststylechem_bt_stylesave_onclicked '(st_layer re_offset re_offset2) 0 "Choix de l'axe des bandes :" 'st_btn 'st_btn (es_ext (groupbib-list 0 'st_btn)))
    )
  )
  (axedyn-setrayext '(st_nom ls_style))
  (repdyn-getpoint (ha_polyext projet_md_geststylechem-hach_re_offset) (ha_polyext projet_md_geststylechem-hach_re_offset2))
  (projet_md_geststylechem-bord_st_style (projet_md_geststylechem-hach_re_offset2 "OC-axes"))
)

(defun stylebord-make (in_lon0 assoc arg_3 listbib-min projet_md_geststylechem-bord_re_offset st_pos / re_cote st_style local_5 inters projet_md_geststylechem-poly_st_layer)
  (entdel 'projet_md_geststylechem-poly_re_offset)
  (fas-rtos3 '(st_nom ls_style) (dcl-control-setenabled inters) projet_md_geststylechem-poly_st_layer)
  (setq inters (st_axeid (/ '(st_nom ls_style))))
  (setq projet_md_geststylechem-poly_st_layer (es_ext (groupbib-list 'ls_obj in_lon0) (groupbib-list '*st_axedynid* assoc) (groupbib-list "Impossible de générer les polylignes contours" arg_3) (groupbib-list 'intersbib-getinsidevtxs listbib-min) (groupbib-list "ls_pano" projet_md_geststylechem-bord_re_offset) (groupbib-list "\n Vérification des panneaux..." projet_md_geststylechem-bord_re_offset) (groupbib-list 'ls_polyhach st_pos)))
  inters
)

(defun stylechem-list (/ local_0 local_1)
  (entdel 'c:projet_md_geststylechem_bt_stylecancel_onclicked)
  (if (cadr (axedyn-setrayext '(ls_style st_nom st_layer st_blkname)))
    (progn
      (c:projet_md_geststylerep_st_blkname_onselchanged 'c:projet_md_geststylechem_bt_stylesave_onclicked 'c:projet_md_geststylerep_btn_copy_onclicked (es_ext (es_ext (groupbib-list 'st_type 're_rayii) (groupbib-list "Repère" 'st_btn) (groupbib-list "re_rayee" '(st_blkname))) (es_ext (groupbib-list 'st_type 're_rayii) (groupbib-list "Repère" 'st_btn) (groupbib-list "re_rayee" "C:\\Pliver\\bib\\900-Développement\\0-Blibilothèque métier\\Panneaux.csv"))))
    )
  )
  (axedyn-setrayext '(ls_style st_nom st_layer st_blkname))
  (repdyn-getpoint (in_param (eo_polyabs projet_md_geststylechem-hach_re_offset) 'ls_obj) (in_param (eo_polyabs projet_md_geststylechem-hach_re_offset2) 'ls_obj))
  (projet_md_geststylechem-bord_st_style (projet_md_geststylechem-hach_re_offset2 '(lambda (x) nil)))
)

(defun stylechem-get (en_rayon / gvar_2519)
  (entdel 'projet_md_geststylechem-bord_re_cote)
  (if (and en_rayon (setq gvar_2519 (re_courant '(ls_style st_nom st_layer st_blkname) en_rayon)))
    (progn
      gvar_2519
    )
    (progn
      (re_courant '(ls_style st_nom st_layer st_blkname) 'metbib-metzgo)
    )
  )
)

(defun c:projet_md_geststylechem-hach_oninitialize (/ blkbib-getparententities gvar_2408 ls_bords)
  (entdel 'projet_md_typeligne_st_mod)
  (if re_rayei
    (progn
      (setq blkbib-getparententities (in_param re_rayei "Repère"))
      (setq gvar_2408 (in_param re_rayei "re_rayee"))
      (setq ls_bords (in_param re_rayei '(lambda (ls_elem) (= "B" (listbib-key ls_elem "st_type")))))
    )
    (progn
      (setq blkbib-getparententities 'st_btn)
      (setq gvar_2408 'ha_poly)
      (setq ls_bords 'en_poly)
    )
  )
  (bo_lctabs gvar_192 blkbib-getparententities)
  (bo_lctabs gvar_191 (eo_blkbase gvar_2408 2 3))
  (bo_lctabs typelinebib-maketype (eo_blkbase ls_bords 2 3))
)

(defun c:projet_md_geststylechem-hach_bt_cancel_onclicked (/ re_rayei)
  (re_abs1 entbib-lshandle2lsent 2)
)

(defun c:projet_md_geststylechem-hach_bt_ok_onclicked ()
  (re_abs1 entbib-lshandle2lsent 1)
)

(defun c:projet_md_geststylechem-bord_oninitialize (/ ha_poly2 gvar_2827 gvar_2408 ls_axe gvar_1346)
  (entdel "CANNOSCALEVALUE")
  (metquantprix gvar_188)
  (metquantprix vla-put-linetypescale)
  (ls_polys gvar_188 ha_poly2)
  (ls_polys vla-put-linetypescale (es_ext '(ls_axes ls_axe) "\n Vérification des axes..."))
  (setq ha_poly2 (polybib-lwvertices 'en_int2dc (sivpano-supportupdate)))
  (if re_rayei
    (progn
      (if (odclbib-fillcombo (in_param re_rayei 'ls_croiselems) 1)
        (progn
          1
        )
        (progn
          0
        )
      )
      (setq gvar_2827 nil)
      (setq gvar_2408 (in_param re_rayei "re_rayee"))
      (setq ls_axe (in_param re_rayei 'dcl-form-show))
      (setq gvar_1346 (laybib-newlay ls_axe (polybib-lwvertices 'axedyn-reaccreate (sivpano-supportupdate))))
    )
    (progn
      (setq gvar_2827 0)
      (setq gvar_2408 'ha_poly)
      (setq gvar_1346 0)
    )
  )
  (if (cadr gvar_1346)
    (progn
      (setq gvar_1346 0)
    )
  )
  (bo_lctabs projet_md_apercu (eo_blkbase gvar_2408 2 3))
  (bo_invpoly1 vla-put-linetypescale gvar_2827)
  (bo_invpoly1 gvar_188 gvar_1346)
)

(defun c:projet_md_geststylechem-bord_bt_cancel_onclicked ()
  (re_abs1 en_poly_som 2)
)

(defun c:projet_md_geststylechem-bord_bt_ok_onclicked (/ gvar_2408 gvar_2827 ls_axe)
  (entdel 'c:projet_md_typeligne_bt_preview_onclicked)
  (setq gvar_2408 (groupbib-listobj (errbib-catchapply projet_md_apercu)))
  (if (re_angle 1 (ls_props2 vla-put-linetypescale))
    (progn
      'en_poly
    )
    (progn
      '(va_point re_abs pt_base pt_1 pt_2 re_abs1 re_abs2)
    )
  )
  (setq gvar_2827 nil)
  (setq ls_axe (dcl-grid-addrow (ls_props2 gvar_188) (polybib-lwvertices 'axedyn-reaccreate (sivpano-supportupdate))))
  (re_abs1 en_poly_som 1)
)

(defun c:projet_md_geststylechem-poly_oninitialize (/ blkbib-getparententities gvar_2408)
  (if re_rayei
    (progn
      (setq blkbib-getparententities (in_param re_rayei "Repère"))
      (setq gvar_2408 (in_param re_rayei "re_rayee"))
    )
    (progn
      (setq blkbib-getparententities 'st_btn)
      (setq gvar_2408 'ha_poly)
    )
  )
  (bo_lctabs gvar_192 blkbib-getparententities)
  (bo_lctabs gvar_191 (eo_blkbase gvar_2408 2 3))
)

(defun c:projet_md_geststylechem-poly_bt_cancel_onclicked ()
  (re_abs1 gvar_225 2)
)

(defun c:projet_md_geststylechem-poly_bt_ok_onclicked ()
  (re_abs1 gvar_225 1)
)

(defun c:projet_md_geststylechem-signa_oninitialize (/ projet_md_typeligne_st_nom gvar_181_c:projet_md_typeligne_st_nom_onsetfocus croisdyn-getparents ld_crois gvar_2406 blkbib-getparententities gvar_2827 sivpano-getnom)
  (metquantprix projet_md_typeligne_st_desc)
  (metquantprix gvar_179_c:projet_md_typeligne_st_desc_onsetfocus)
  (metquantprix gvar_178_c:projet_md_typeligne_st_txt_onsetfocus)
  (metquantprix gvar_177_c:projet_md_typeligne_st_mod_onsetfocus)
  (ls_polys projet_md_typeligne_st_desc (polybib-lwvertices 'eo_polyabs gvar_181_c:projet_md_typeligne_st_nom_onsetfocus))
  (ls_polys gvar_177_c:projet_md_typeligne_st_mod_onsetfocus (es_ext '(ls_axes ls_axe) 'sivpano-getbase "\n Vérification des axes..."))
  (ls_polys gvar_179_c:projet_md_typeligne_st_desc_onsetfocus (polybib-lwvertices 're_x projet_md_typeligne_st_nom))
  (setq projet_md_typeligne_st_nom (eo_sup))
  (setq gvar_181_c:projet_md_typeligne_st_nom_onsetfocus (es_ext (groupbib-list 'sihpp-popgo 'ls_sir-ver) (groupbib-list 'st_pano 'fl_fin) (groupbib-list 'sivpano-listpano '(en_sup eo_sup pt_base re_offset st_panneau ls_att)) (groupbib-list '*st_metier* '*blockpath*)))
  (if re_rayei
    (progn
      (setq croisdyn-getparents (in_param re_rayei 'croisdyn-set))
      (setq ld_crois (in_param re_rayei "ha_contour"))
      (setq gvar_2406 (in_param re_rayei "re_rayie"))
      (setq blkbib-getparententities (in_param re_rayei "Repère"))
      (setq gvar_2827 (in_param re_rayei 'ls_croiselems))
    )
    (progn
      (setq croisdyn-getparents 'oc-typelignedial-new)
      (setq ld_crois "Support précédent effacé, copie impossible")
      (setq gvar_2406 'st_pano)
      (setq blkbib-getparententities 'st_btn)
      (setq gvar_2827 'en_poly)
    )
  )
  (if gvar_2827
    (progn
      (bo_invpoly1 gvar_177_c:projet_md_typeligne_st_mod_onsetfocus (st_axeid gvar_2827))
    )
    (progn
      (bo_invpoly1 gvar_177_c:projet_md_typeligne_st_mod_onsetfocus 1)
    )
  )
  (bo_invpoly1 gvar_179_c:projet_md_typeligne_st_desc_onsetfocus (laybib-newlay ld_crois (polybib-lwvertices 'axedyn-reaccreate projet_md_typeligne_st_nom)))
  (bo_invpoly1 projet_md_typeligne_st_desc (laybib-newlay gvar_2406 (polybib-lwvertices 'axedyn-reaccreate gvar_181_c:projet_md_typeligne_st_nom_onsetfocus)))
  (ls_polys gvar_178_c:projet_md_typeligne_st_txt_onsetfocus sivpano-getnom)
  (bo_invpoly1 gvar_178_c:projet_md_typeligne_st_txt_onsetfocus (laybib-newlay croisdyn-getparents sivpano-getnom))
  (setq sivpano-getnom (va_bande (dcl-grid-addrow (laybib-newlay ld_crois (polybib-lwvertices 'axedyn-reaccreate projet_md_typeligne_st_nom)) projet_md_typeligne_st_nom)))
  (bo_lctabs gvar_175_c:projet_md_typeligne_bt_new_onclicked blkbib-getparententities)
)

(defun c:projet_md_geststylechem-signa_st_mod_onselchanged (/ eo_poly arg_2)
  (metquantprix gvar_178_c:projet_md_typeligne_st_txt_onsetfocus)
  (ls_polys gvar_178_c:projet_md_typeligne_st_txt_onsetfocus (va_bande (dcl-grid-addrow eo_poly_2 projet_md_typeligne_st_nom)))
  (bo_invpoly1 gvar_178_c:projet_md_typeligne_st_txt_onsetfocus 0)
  (ls_som0)
)

(defun c:projet_md_geststylechem-signa_bt_ok_onclicked (/ gvar_2408 blkbib-getparententities gvar_2406 ld_crois croisdyn-getparents gvar_2827)
  (entdel 'c:projet_md_typeligne_bt_ok_onclicked)
  (setq gvar_2408 (groupbib-listobj (errbib-catchapply gvar_173)))
  (setq blkbib-getparententities (errbib-catchapply gvar_175_c:projet_md_typeligne_bt_new_onclicked))
  (setq gvar_2406 (dcl-grid-addrow (ls_props2 projet_md_typeligne_st_desc) (polybib-lwvertices 'axedyn-reaccreate gvar_181_c:projet_md_typeligne_st_nom_onsetfocus)))
  (setq ld_crois (dcl-grid-addrow (ls_props2 gvar_179_c:projet_md_typeligne_st_desc_onsetfocus) (polybib-lwvertices 'axedyn-reaccreate projet_md_typeligne_st_nom)))
  (setq croisdyn-getparents (dcl-grid-addrow (ls_props2 gvar_178_c:projet_md_typeligne_st_txt_onsetfocus) (va_bande (dcl-grid-addrow (ls_props2 gvar_179_c:projet_md_typeligne_st_desc_onsetfocus) projet_md_typeligne_st_nom))))
  (setq gvar_2827 (dcl-grid-addrow (ls_props2 gvar_177_c:projet_md_typeligne_st_mod_onsetfocus) (es_ext '(va_point re_abs pt_base pt_1 pt_2 re_abs1 re_abs2) 'ha_poly 'en_poly)))
  (re_abs1 taldyn-get 1)
)

(defun c:projet_md_geststylechem-signa_bt_cancel_onclicked ()
  (re_abs1 taldyn-get 2)
)

(defun stylepoly-list (/ local_0 local_1)
  (if (cadr (axedyn-setrayext "LTYPE"))
    (progn
      (projet_md_typeligne_st_msg 'projet_md_typeligne_st_msg 'st_btn '(lambda (ls_filter) (cons (itoa (car ls_filter)) (cdr ls_filter))))
    )
  )
  (axedyn-setrayext "LTYPE")
  (repdyn-getpoint (ha_polyext projet_md_geststylechem-hach_re_offset) (ha_polyext projet_md_geststylechem-hach_re_offset2))
  (projet_md_geststylechem-bord_st_style (projet_md_geststylechem-hach_re_offset2 "ls_ray"))
)

(defun stylepoly-fillcombo (c:projet_md_apercu_vueblocs1_onclicked ls_axe / ha_poly2)
  (entdel 'c:projet_md_typeligne_bt_close_onclicked)
  (metquantprix c:projet_md_apercu_vueblocs1_onclicked)
  (setq ha_poly2 (ls_dist))
  (if c:projet_md_apercu_vueblocs1_onclicked
    (progn
      (ls_polys c:projet_md_apercu_vueblocs1_onclicked (polybib-lwvertices 'ha_polyext ha_poly2))
      (if (and ls_axe (laybib-newlay ls_axe (polybib-lwvertices 'axedyn-reaccreate ha_poly2)))
        (progn
          (bo_invpoly1 c:projet_md_apercu_vueblocs1_onclicked (laybib-newlay ls_axe (polybib-lwvertices 'axedyn-reaccreate ha_poly2)))
        )
        (progn
          (bo_invpoly1 c:projet_md_apercu_vueblocs1_onclicked 0)
        )
      )
    )
    (progn
      nil
    )
  )
)

(defun stylerep-list (/ local_0 local_1)
  (entdel 'c:projet_md_geststylechem_bt_stylecancel_onclicked)
  (if (cadr (axedyn-setrayext '((cons 160057 160136) (cons 160015 160037) (cons 159981 159995) (cons 159872 159961) (cons 159633 159861) (cons 159581 159613) (cons 159550 159561) (cons 159512 159530) (cons 159474 159492) (cons 159436 159454) (cons 159398 159416) (cons 159355 159378) (cons 159125 159335) (cons 159029 159105) (cons 159009 160606) (cons 158980 159009) (cons 158907 158980) (cons 158666 158907) (cons 158636 158666) (cons 158601 158636) (cons 158583 158601) (cons 158359 158583) (cons 158327 158359) (cons 157400 158327) (cons 157242 157400) (cons 156941 157242) (cons 156903 156941) (cons 156874 156903) (cons 156860 156874) (cons 156799 156821) (cons 156767 156779) (cons 156544 156747) (cons 156468 156524) (cons 156305 156448) (cons 156187 156285) (cons 156125 156167) (cons 156076 156105) (cons 155840 156056) (cons 155779 155820) (cons 155623 155768) (cons 155490 155612) (cons 155470 156860) (cons 155350 155470) (cons 155287 155332) (cons 155226 155260) (cons 155168 155350) (cons 155060 155168) (cons 155003 155019) (cons 154805 154983) (cons 154686 154785) (cons 154624 154666) (cons 154554 154604) (cons 154340 154534) (cons 154167 154329) (cons 154109 154156) (cons 154057 154089) (cons 154037 155060) (cons 153872 154037) (cons 153792 153872) (cons 153682 153792) (cons 153622 153667) (cons 153566 153682) (cons 153458 153566) (cons 153442 153458) (cons 153180 153442) (cons 153106 153180) (cons 152653 153106) (cons 152581 152653) (cons 152565 152581) (cons 152474 152565) (cons 152314 152474) (cons 152298 152314) (cons 152030 152298) (cons 151937 152030) (cons 151915 151937) (cons 151770 151915) (cons 151644 151746) (cons 151541 151624) (cons 151466 151521) (cons 151391 151446) (cons 151316 151371) (cons 151228 151296) (cons 151075 151208) (cons 150795 151064) (cons 150355 150784) (cons 150319 150335) (cons 150274 150299) (cons 149934 150254) (cons 149859 149914) (cons 149825 149839) (cons 149668 149805) (cons 149543 149648) (cons 149392 149523) (cons 149272 149381) (cons 149220 149252) (cons 149210 151770) (cons 149082 149210) (cons 149044 149082) (cons 148963 149044) (cons 148884 148945) (cons 148740 148963) (cons 148697 148713) (cons 148642 148677) (cons 148377 148622) (cons 148273 148357) (cons 148236 148253) (cons 148106 148216) (cons 147954 148086) (cons 147922 147934) (cons 147387 147902) (cons 147268 147367) (cons 146513 147248) (cons 146475 146493) (cons 146437 146455) (cons 146399 146417) (cons 146337 146379) (cons 146248 146317) (cons 146192 146228) (cons 146016 146172) (cons 145922 145996) (cons 145729 145902) (cons 145659 145718) (cons 145504 145648) (cons 145254 145493) (cons 145144 145243) (cons 145124 148740) (cons 144936 145124) (cons 144855 144936) (cons 144792 144837) (cons 144703 144855) (cons 144551 144703) (cons 144400 144551) (cons 144169 144400) (cons 144056 144169) (cons 143818 144056) (cons 143691 143818) (cons 143632 143691) (cons 143376 143632) (cons 143067 143376) (cons 142986 143067) (cons 142880 142986) (cons 142715 142880) (cons 142287 142715) (cons 141993 142039) (cons 141771 141973) (cons 141713 141751) (cons 141675 141693) (cons 141506 141664) (cons 141393 141486) (cons 141241 141373) (cons 141153 141230) (cons 141037 141133) (cons 140933 141017) (cons 140668 140913) (cons 140332 140657) (cons 140179 140312) (cons 140053 142287) (cons 139810 140053) (cons 139772 139810) (cons 139756 139772) (cons 139740 139756) (cons 139649 139740) (cons 139592 139649) (cons 139535 139592) (cons 139179 139535) (cons 139047 139179) (cons 138935 139047) (cons 138645 138935) (cons 138391 138645) (cons 138192 138391) (cons 137627 138192) (cons 137171 137627) (cons 136723 137171) (cons 136167 136723) (cons 135993 136167) (cons 135627 135993) (cons 135347 135627) (cons 135311 135347) (cons 135273 135311) (cons 135244 135273) (cons 135230 135244) (cons 135201 135230) (cons 135154 135201) (cons 135045 135154) (cons 134939 135045) (cons 134833 134939) (cons 134727 134833) (cons 134709 134727) (cons 134691 134709) (cons 134622 134691) (cons 134347 134622) (cons 134309 134347) (cons 133498 134309) (cons 131945 133498) (cons 131669 131945) (cons 131464 131669) (cons 131295 131464) (cons 130964 131295) (cons 130950 130964) (cons 130912 130950) (cons 130883 130912) (cons 130869 130883) (cons 130723 130836) (cons 130559 130703) (cons 130352 130539) (cons 130155 130869) (cons 130118 130155) (cons 130040 130118) (cons 129971 130040) (cons 129744 129971) (cons 129612 129744) (cons 129142 129612) (cons 129110 129142) (cons 128362 128830) (cons 128291 129110) (cons 127764 128291) (cons 127755 127764) (cons 127603 127755) (cons 127460 127603) (cons 127302 127460) (cons 127013 127302) (cons 126975 127013) (cons 126946 126975) (cons 126932 126946) (cons 126766 126932) (cons 126708 126766) (cons 126618 126708) (cons 126243 126618) (cons 126184 126243) (cons 126173 126184) (cons 125882 126173) (cons 125864 125882) (cons 125846 125864) (cons 125828 125846) (cons 125810 125828) (cons 125792 125810) (cons 125751 125792) (cons 125726 125751) (cons 125654 125726) (cons 125623 125654) (cons 125022 125623) (cons 124953 125022) (cons 124303 124953) (cons 124265 124303) (cons 123656 124265) (cons 122913 123656) (cons 122303 122913) (cons 122145 122303) (cons 121670 122145) (cons 121632 121670) (cons 121603 121632) (cons 121589 121603) (cons 121444 121589) (cons 121252 121444) (cons 121233 121252) (cons 121217 121233) (cons 120197 121217) (cons 119780 120197) (cons 119499 119780) (cons 118725 119499) (cons 118560 118725) (cons 118187 118560) (cons 117951 118187) (cons 117762 117951) (cons 117187 117762) (cons 116053 117187) (cons 115853 116053) (cons 115664 115853) (cons 115514 115664) (cons 115393 115514) (cons 115035 115393) (cons 114997 115035) (cons 114968 114997) (cons 114954 114968) (cons 114925 114954) (cons 114819 114925) (cons 114669 114819) (cons 114439 114669) (cons 114209 114439) (cons 114191 114209) (cons 113935 114191) (cons 113897 113935) (cons 113528 113897) (cons 113253 113528) (cons 112435 113253) (cons 111704 112435) (cons 111666 111704) (cons 111637 111666) (cons 111623 111637) (cons 111058 111176) (cons 110815 111047) (cons 110502 110804) (cons 110189 110491) (cons 109964 110178) (cons 109749 109953) (cons 109523 109738) (cons 109274 109512) (cons 109049 109263) (cons 109014 111623) (cons 108961 109014) (cons 108687 108961) (cons 108385 108687) (cons 108321 108385) (cons 108263 108321) (cons 108001 108263) (cons 107544 108001) (cons 107520 107544) (cons 107083 107520) (cons 106578 107083) (cons 106183 106578) (cons 105759 106183) (cons 104942 105759) (cons 104672 104942) (cons 104440 104672) (cons 103671 104440) (cons 103310 103671) (cons 102920 103310) (cons 102818 102920) (cons 102781 102818) (cons 102677 102781) (cons 102444 102677) (cons 102064 102444) (cons 102046 102064) (cons 102028 102046) (cons 102010 102028) (cons 101992 102010) (cons 101785 101992) (cons 101591 101785) (cons 101577 101591) (cons 101550 101577) (cons 101229 101550) (cons 101051 101229) (cons 99879 101051) (cons 99815 99879) (cons 99509 99815) (cons 99313 99509) (cons 99073 99313) (cons 98595 99073) (cons 98174 98595) (cons 97934 98174) (cons 97787 97934) (cons 96110 97787) (cons 95955 96110) (cons 95721 95955) (cons 95551 95721) (cons 95159 95551) (cons 94807 95159) (cons 94494 94807) (cons 94045 94494) (cons 93996 94045) (cons 93807 93996) (cons 93594 93807) (cons 93556 93594) (cons 93527 93556) (cons 93513 93527) (cons 93415 93465) (cons 93368 93395) (cons 93261 93348) (cons 93004 93241) (cons 92975 93513) (cons 92877 92975) (cons 92785 92877) (cons 92769 92785) (cons 92752 92769) (cons 92725 92752) (cons 92667 92725) (cons 92647 92667) (cons 92580 92647) (cons 92452 92580) (cons 92124 92452) (cons 90651 92124) (cons 90495 90651) (cons 90273 90495) (cons 90205 90273) (cons 90135 90205) (cons 89973 90135) (cons 89901 89973) (cons 89463 89901) (cons 89434 89463) (cons 89254 89434) (cons 89225 89254) (cons 89009 89225) (cons 88828 89009) (cons 88647 88828) (cons 88377 88647) (cons 87867 88377) (cons 87494 87867) (cons 86354 87494) (cons 86319 86354) (cons 85749 86319) (cons 85581 85749) (cons 85200 85581) (cons 85151 85200) (cons 84652 85151) (cons 84423 84652) (cons 84133 84423) (cons 83802 84133) (cons 83450 83802) (cons 83049 83450) (cons 82985 83049) (cons 82808 82985) (cons 82794 82808) (cons 82486 82794) (cons 82324 82486) (cons 82191 82324) (cons 81864 82191) (cons 81740 81864) (cons 81513 81740) (cons 81322 81513) (cons 80931 81322) (cons 80319 80931) (cons 79935 80319) (cons 79800 79935) (cons 79618 79800) (cons 79171 79618) (cons 79005 79054) (cons 78885 78985) (cons 78849 78865) (cons 78811 78829) (cons 78773 78791) (cons 78603 78753) (cons 78562 79171) (cons 78546 78562) (cons 78393 78546) (cons 77922 78393) (cons 77785 77922) (cons 77258 77785) (cons 76632 77258) (cons 76603 76632) (cons 76263 76603) (cons 75612 76263) (cons 75549 75612) (cons 75394 75549) (cons 75250 75394) (cons 75090 75250) (cons 74876 75090) (cons 74680 74876) (cons 74592 74680) (cons 74440 74592) (cons 74307 74440) (cons 74193 74307) (cons 73977 74193) (cons 73723 73977) (cons 73541 73723) (cons 73488 73541) (cons 73354 73488) (cons 73282 73354) (cons 73165 73282) (cons 73056 73165) (cons 72750 73056) (cons 72734 72750) (cons 72625 72734) (cons 72580 72625) (cons 72525 72580) (cons 72470 72525) (cons 72296 72470) (cons 71573 72296) (cons 71512 71573) (cons 71496 71512) (cons 71480 71496) (cons 71464 71480) (cons 71447 71464) (cons 71332 71447) (cons 71100 71332) (cons 70977 71100) (cons 70825 70977) (cons 70509 70825) (cons 70468 70509) (cons 70121 70147) (cons 69647 70101) (cons 69591 69627) (cons 69535 69571) (cons 69460 69515) (cons 68268 69440) (cons 68232 68248) (cons 68194 68212) (cons 68156 68174) (cons 68109 70468) (cons 67577 68109) (cons 67286 67577) (cons 67189 67286) (cons 66641 67189) (cons 64343 66641) (cons 62808 64343) (cons 62482 62808) (cons 62115 62482) (cons 61791 62115) (cons 61561 61791) (cons 61186 61561) (cons 61063 61186) (cons 60683 61063) (cons 60382 60683) (cons 60108 60382) (cons 59909 60108) (cons 59612 59909) (cons 59315 59612) (cons 59018 59315) (cons 58739 59018) (cons 58543 58739) (cons 58004 58543) (cons 57412 58004) (cons 56866 57412) (cons 56379 56866) (cons 55906 56379) (cons 55757 55906) (cons 55238 55757) (cons 54458 55238) (cons 54442 54458) (cons 54141 54442) (cons 54070 54141) (cons 53934 54070) (cons 53122 53934) (cons 53083 53122) (cons 52572 53083) (cons 52148 52572) (cons 51906 52148) (cons 51501 51906) (cons 51298 51501) (cons 51237 51298) (cons 51064 51237) (cons 50859 51064) (cons 50715 50859) (cons 50550 50715) (cons 50386 50550) (cons 50220 50386) (cons 49985 50220) (cons 49932 49985) (cons 48949 49932) (cons 48910 48949) (cons 48421 48910) (cons 48379 48421) (cons 48338 48379) (cons 48113 48338) (cons 48068 48113) (cons 48023 48068) (cons 47978 48023) (cons 47933 47978) (cons 47498 47933) (cons 47253 47498) (cons 47221 47253) (cons 46464 47221) (cons 45590 46464) (cons 44721 45590) (cons 43281 44721) (cons 42941 43281) (cons 42868 42941) (cons 42554 42868) (cons 42516 42554) (cons 42410 42516) (cons 42396 42410) (cons 41950 42396) (cons 41232 41950) (cons 40442 41232) (cons 39931 40442) (cons 39541 39931) (cons 39497 39541) (cons 39459 39497) (cons 39387 39459) (cons 39207 39387) (cons 39037 39207) (cons 38745 39037) (cons 38713 38745) (cons 38396 38713) (cons 38157 38396) (cons 37656 38157) (cons 37423 37656) (cons 36940 37423) (cons 34753 36940) (cons 34595 34753) (cons 34276 34595) (cons 34238 34276) (cons 34132 34238) (cons 34118 34132) (cons 34089 34118) (cons 34017 34089) (cons 33837 34017) (cons 33807 33837) (cons 33512 33807) (cons 33480 33512) (cons 33248 33480) (cons 32715 33248) (cons 31684 32715) (cons 30753 31684) (cons 30263 30753) (cons 30001 30263) (cons 29784 30001) (cons 29588 29784) (cons 29430 29588) (cons 29111 29430) (cons 29073 29111) (cons 29044 29073) (cons 29030 29044) (cons 28784 29029) (cons 28651 28784) (cons 28578 28606) (cons 28481 28558) (cons 28374 28461) (cons 28291 28354) (cons 28135 28271) (cons 28027 28124) (cons 27580 28007) (cons 27525 27560) (cons 27470 27505) (cons 27394 27450) (cons 27368 28651) (cons 26886 27368) (cons 26496 26886) (cons 26005 26496) (cons 25748 26005) (cons 24908 25748) (cons 24660 24908) (cons 24258 24660) (cons 23643 24258) (cons 23318 23643) (cons 22923 23318) (cons 22494 22923) (cons 22263 22494) (cons 21735 22263) (cons 20632 21735) (cons 20182 20632) (cons 19630 20182) (cons 18248 19630) (cons 17937 18248) (cons 17884 17937) (cons 16657 17884) (cons 16485 16657) (cons 16372 16485) (cons 16337 16372) (cons 15999 16337) (cons 15444 15999) (cons 15306 15444) (cons 15288 15306) (cons 15153 15288) (cons 15034 15153) (cons 14698 15034) (cons 14557 14698) (cons 14232 14557) (cons 14203 14232) (cons 13936 14203) (cons 13851 13936) (cons 13631 13851) (cons 13587 13631) (cons 13555 13587) (cons 13231 13555) (cons 13085 13231) (cons 12391 13085) (cons 11998 12391) (cons 11511 11998) (cons 10871 11511) (cons 10553 10871) (cons 10472 10553) (cons 9233 10472) (cons 7902 9233) (cons 6842 7902) (cons 6597 6842) (cons 6559 6597) (cons 6530 6559) (cons 6516 6530) (cons 6498 6516) (cons 6340 6498) (cons 5992 6340) (cons 5943 5992) (cons 5772 5943) (cons 5315 5772) (cons 5181 5315) (cons 5129 5181) (cons 4920 5129) (cons 4261 4920) (cons 3682 4261) (cons 3021 3682) (cons 2883 3021) (cons 2540 2883) (cons 2342 2540) (cons 1184 2342) (cons 703 1184) (cons 665 703) (cons 636 665) (cons 622 636) (cons 377 622) (cons 1 377))))
    (progn
      (resdyn-palapply 'projet_md_typeligne_st_msg 'st_btn 'c:projet_pa_resdyn_bt_calque_onclicked)
    )
  )
  (in_param (eo_polyabs projet_md_geststylechem-hach_re_offset) 'ls_obj)
  (ls_elem (projet_md_geststylechem-hach_re_offset2 '*ld_mod*) (axedyn-setrayext '((cons 160057 160136) (cons 160015 160037) (cons 159981 159995) (cons 159872 159961) (cons 159633 159861) (cons 159581 159613) (cons 159550 159561) (cons 159512 159530) (cons 159474 159492) (cons 159436 159454) (cons 159398 159416) (cons 159355 159378) (cons 159125 159335) (cons 159029 159105) (cons 159009 160606) (cons 158980 159009) (cons 158907 158980) (cons 158666 158907) (cons 158636 158666) (cons 158601 158636) (cons 158583 158601) (cons 158359 158583) (cons 158327 158359) (cons 157400 158327) (cons 157242 157400) (cons 156941 157242) (cons 156903 156941) (cons 156874 156903) (cons 156860 156874) (cons 156799 156821) (cons 156767 156779) (cons 156544 156747) (cons 156468 156524) (cons 156305 156448) (cons 156187 156285) (cons 156125 156167) (cons 156076 156105) (cons 155840 156056) (cons 155779 155820) (cons 155623 155768) (cons 155490 155612) (cons 155470 156860) (cons 155350 155470) (cons 155287 155332) (cons 155226 155260) (cons 155168 155350) (cons 155060 155168) (cons 155003 155019) (cons 154805 154983) (cons 154686 154785) (cons 154624 154666) (cons 154554 154604) (cons 154340 154534) (cons 154167 154329) (cons 154109 154156) (cons 154057 154089) (cons 154037 155060) (cons 153872 154037) (cons 153792 153872) (cons 153682 153792) (cons 153622 153667) (cons 153566 153682) (cons 153458 153566) (cons 153442 153458) (cons 153180 153442) (cons 153106 153180) (cons 152653 153106) (cons 152581 152653) (cons 152565 152581) (cons 152474 152565) (cons 152314 152474) (cons 152298 152314) (cons 152030 152298) (cons 151937 152030) (cons 151915 151937) (cons 151770 151915) (cons 151644 151746) (cons 151541 151624) (cons 151466 151521) (cons 151391 151446) (cons 151316 151371) (cons 151228 151296) (cons 151075 151208) (cons 150795 151064) (cons 150355 150784) (cons 150319 150335) (cons 150274 150299) (cons 149934 150254) (cons 149859 149914) (cons 149825 149839) (cons 149668 149805) (cons 149543 149648) (cons 149392 149523) (cons 149272 149381) (cons 149220 149252) (cons 149210 151770) (cons 149082 149210) (cons 149044 149082) (cons 148963 149044) (cons 148884 148945) (cons 148740 148963) (cons 148697 148713) (cons 148642 148677) (cons 148377 148622) (cons 148273 148357) (cons 148236 148253) (cons 148106 148216) (cons 147954 148086) (cons 147922 147934) (cons 147387 147902) (cons 147268 147367) (cons 146513 147248) (cons 146475 146493) (cons 146437 146455) (cons 146399 146417) (cons 146337 146379) (cons 146248 146317) (cons 146192 146228) (cons 146016 146172) (cons 145922 145996) (cons 145729 145902) (cons 145659 145718) (cons 145504 145648) (cons 145254 145493) (cons 145144 145243) (cons 145124 148740) (cons 144936 145124) (cons 144855 144936) (cons 144792 144837) (cons 144703 144855) (cons 144551 144703) (cons 144400 144551) (cons 144169 144400) (cons 144056 144169) (cons 143818 144056) (cons 143691 143818) (cons 143632 143691) (cons 143376 143632) (cons 143067 143376) (cons 142986 143067) (cons 142880 142986) (cons 142715 142880) (cons 142287 142715) (cons 141993 142039) (cons 141771 141973) (cons 141713 141751) (cons 141675 141693) (cons 141506 141664) (cons 141393 141486) (cons 141241 141373) (cons 141153 141230) (cons 141037 141133) (cons 140933 141017) (cons 140668 140913) (cons 140332 140657) (cons 140179 140312) (cons 140053 142287) (cons 139810 140053) (cons 139772 139810) (cons 139756 139772) (cons 139740 139756) (cons 139649 139740) (cons 139592 139649) (cons 139535 139592) (cons 139179 139535) (cons 139047 139179) (cons 138935 139047) (cons 138645 138935) (cons 138391 138645) (cons 138192 138391) (cons 137627 138192) (cons 137171 137627) (cons 136723 137171) (cons 136167 136723) (cons 135993 136167) (cons 135627 135993) (cons 135347 135627) (cons 135311 135347) (cons 135273 135311) (cons 135244 135273) (cons 135230 135244) (cons 135201 135230) (cons 135154 135201) (cons 135045 135154) (cons 134939 135045) (cons 134833 134939) (cons 134727 134833) (cons 134709 134727) (cons 134691 134709) (cons 134622 134691) (cons 134347 134622) (cons 134309 134347) (cons 133498 134309) (cons 131945 133498) (cons 131669 131945) (cons 131464 131669) (cons 131295 131464) (cons 130964 131295) (cons 130950 130964) (cons 130912 130950) (cons 130883 130912) (cons 130869 130883) (cons 130723 130836) (cons 130559 130703) (cons 130352 130539) (cons 130155 130869) (cons 130118 130155) (cons 130040 130118) (cons 129971 130040) (cons 129744 129971) (cons 129612 129744) (cons 129142 129612) (cons 129110 129142) (cons 128362 128830) (cons 128291 129110) (cons 127764 128291) (cons 127755 127764) (cons 127603 127755) (cons 127460 127603) (cons 127302 127460) (cons 127013 127302) (cons 126975 127013) (cons 126946 126975) (cons 126932 126946) (cons 126766 126932) (cons 126708 126766) (cons 126618 126708) (cons 126243 126618) (cons 126184 126243) (cons 126173 126184) (cons 125882 126173) (cons 125864 125882) (cons 125846 125864) (cons 125828 125846) (cons 125810 125828) (cons 125792 125810) (cons 125751 125792) (cons 125726 125751) (cons 125654 125726) (cons 125623 125654) (cons 125022 125623) (cons 124953 125022) (cons 124303 124953) (cons 124265 124303) (cons 123656 124265) (cons 122913 123656) (cons 122303 122913) (cons 122145 122303) (cons 121670 122145) (cons 121632 121670) (cons 121603 121632) (cons 121589 121603) (cons 121444 121589) (cons 121252 121444) (cons 121233 121252) (cons 121217 121233) (cons 120197 121217) (cons 119780 120197) (cons 119499 119780) (cons 118725 119499) (cons 118560 118725) (cons 118187 118560) (cons 117951 118187) (cons 117762 117951) (cons 117187 117762) (cons 116053 117187) (cons 115853 116053) (cons 115664 115853) (cons 115514 115664) (cons 115393 115514) (cons 115035 115393) (cons 114997 115035) (cons 114968 114997) (cons 114954 114968) (cons 114925 114954) (cons 114819 114925) (cons 114669 114819) (cons 114439 114669) (cons 114209 114439) (cons 114191 114209) (cons 113935 114191) (cons 113897 113935) (cons 113528 113897) (cons 113253 113528) (cons 112435 113253) (cons 111704 112435) (cons 111666 111704) (cons 111637 111666) (cons 111623 111637) (cons 111058 111176) (cons 110815 111047) (cons 110502 110804) (cons 110189 110491) (cons 109964 110178) (cons 109749 109953) (cons 109523 109738) (cons 109274 109512) (cons 109049 109263) (cons 109014 111623) (cons 108961 109014) (cons 108687 108961) (cons 108385 108687) (cons 108321 108385) (cons 108263 108321) (cons 108001 108263) (cons 107544 108001) (cons 107520 107544) (cons 107083 107520) (cons 106578 107083) (cons 106183 106578) (cons 105759 106183) (cons 104942 105759) (cons 104672 104942) (cons 104440 104672) (cons 103671 104440) (cons 103310 103671) (cons 102920 103310) (cons 102818 102920) (cons 102781 102818) (cons 102677 102781) (cons 102444 102677) (cons 102064 102444) (cons 102046 102064) (cons 102028 102046) (cons 102010 102028) (cons 101992 102010) (cons 101785 101992) (cons 101591 101785) (cons 101577 101591) (cons 101550 101577) (cons 101229 101550) (cons 101051 101229) (cons 99879 101051) (cons 99815 99879) (cons 99509 99815) (cons 99313 99509) (cons 99073 99313) (cons 98595 99073) (cons 98174 98595) (cons 97934 98174) (cons 97787 97934) (cons 96110 97787) (cons 95955 96110) (cons 95721 95955) (cons 95551 95721) (cons 95159 95551) (cons 94807 95159) (cons 94494 94807) (cons 94045 94494) (cons 93996 94045) (cons 93807 93996) (cons 93594 93807) (cons 93556 93594) (cons 93527 93556) (cons 93513 93527) (cons 93415 93465) (cons 93368 93395) (cons 93261 93348) (cons 93004 93241) (cons 92975 93513) (cons 92877 92975) (cons 92785 92877) (cons 92769 92785) (cons 92752 92769) (cons 92725 92752) (cons 92667 92725) (cons 92647 92667) (cons 92580 92647) (cons 92452 92580) (cons 92124 92452) (cons 90651 92124) (cons 90495 90651) (cons 90273 90495) (cons 90205 90273) (cons 90135 90205) (cons 89973 90135) (cons 89901 89973) (cons 89463 89901) (cons 89434 89463) (cons 89254 89434) (cons 89225 89254) (cons 89009 89225) (cons 88828 89009) (cons 88647 88828) (cons 88377 88647) (cons 87867 88377) (cons 87494 87867) (cons 86354 87494) (cons 86319 86354) (cons 85749 86319) (cons 85581 85749) (cons 85200 85581) (cons 85151 85200) (cons 84652 85151) (cons 84423 84652) (cons 84133 84423) (cons 83802 84133) (cons 83450 83802) (cons 83049 83450) (cons 82985 83049) (cons 82808 82985) (cons 82794 82808) (cons 82486 82794) (cons 82324 82486) (cons 82191 82324) (cons 81864 82191) (cons 81740 81864) (cons 81513 81740) (cons 81322 81513) (cons 80931 81322) (cons 80319 80931) (cons 79935 80319) (cons 79800 79935) (cons 79618 79800) (cons 79171 79618) (cons 79005 79054) (cons 78885 78985) (cons 78849 78865) (cons 78811 78829) (cons 78773 78791) (cons 78603 78753) (cons 78562 79171) (cons 78546 78562) (cons 78393 78546) (cons 77922 78393) (cons 77785 77922) (cons 77258 77785) (cons 76632 77258) (cons 76603 76632) (cons 76263 76603) (cons 75612 76263) (cons 75549 75612) (cons 75394 75549) (cons 75250 75394) (cons 75090 75250) (cons 74876 75090) (cons 74680 74876) (cons 74592 74680) (cons 74440 74592) (cons 74307 74440) (cons 74193 74307) (cons 73977 74193) (cons 73723 73977) (cons 73541 73723) (cons 73488 73541) (cons 73354 73488) (cons 73282 73354) (cons 73165 73282) (cons 73056 73165) (cons 72750 73056) (cons 72734 72750) (cons 72625 72734) (cons 72580 72625) (cons 72525 72580) (cons 72470 72525) (cons 72296 72470) (cons 71573 72296) (cons 71512 71573) (cons 71496 71512) (cons 71480 71496) (cons 71464 71480) (cons 71447 71464) (cons 71332 71447) (cons 71100 71332) (cons 70977 71100) (cons 70825 70977) (cons 70509 70825) (cons 70468 70509) (cons 70121 70147) (cons 69647 70101) (cons 69591 69627) (cons 69535 69571) (cons 69460 69515) (cons 68268 69440) (cons 68232 68248) (cons 68194 68212) (cons 68156 68174) (cons 68109 70468) (cons 67577 68109) (cons 67286 67577) (cons 67189 67286) (cons 66641 67189) (cons 64343 66641) (cons 62808 64343) (cons 62482 62808) (cons 62115 62482) (cons 61791 62115) (cons 61561 61791) (cons 61186 61561) (cons 61063 61186) (cons 60683 61063) (cons 60382 60683) (cons 60108 60382) (cons 59909 60108) (cons 59612 59909) (cons 59315 59612) (cons 59018 59315) (cons 58739 59018) (cons 58543 58739) (cons 58004 58543) (cons 57412 58004) (cons 56866 57412) (cons 56379 56866) (cons 55906 56379) (cons 55757 55906) (cons 55238 55757) (cons 54458 55238) (cons 54442 54458) (cons 54141 54442) (cons 54070 54141) (cons 53934 54070) (cons 53122 53934) (cons 53083 53122) (cons 52572 53083) (cons 52148 52572) (cons 51906 52148) (cons 51501 51906) (cons 51298 51501) (cons 51237 51298) (cons 51064 51237) (cons 50859 51064) (cons 50715 50859) (cons 50550 50715) (cons 50386 50550) (cons 50220 50386) (cons 49985 50220) (cons 49932 49985) (cons 48949 49932) (cons 48910 48949) (cons 48421 48910) (cons 48379 48421) (cons 48338 48379) (cons 48113 48338) (cons 48068 48113) (cons 48023 48068) (cons 47978 48023) (cons 47933 47978) (cons 47498 47933) (cons 47253 47498) (cons 47221 47253) (cons 46464 47221) (cons 45590 46464) (cons 44721 45590) (cons 43281 44721) (cons 42941 43281) (cons 42868 42941) (cons 42554 42868) (cons 42516 42554) (cons 42410 42516) (cons 42396 42410) (cons 41950 42396) (cons 41232 41950) (cons 40442 41232) (cons 39931 40442) (cons 39541 39931) (cons 39497 39541) (cons 39459 39497) (cons 39387 39459) (cons 39207 39387) (cons 39037 39207) (cons 38745 39037) (cons 38713 38745) (cons 38396 38713) (cons 38157 38396) (cons 37656 38157) (cons 37423 37656) (cons 36940 37423) (cons 34753 36940) (cons 34595 34753) (cons 34276 34595) (cons 34238 34276) (cons 34132 34238) (cons 34118 34132) (cons 34089 34118) (cons 34017 34089) (cons 33837 34017) (cons 33807 33837) (cons 33512 33807) (cons 33480 33512) (cons 33248 33480) (cons 32715 33248) (cons 31684 32715) (cons 30753 31684) (cons 30263 30753) (cons 30001 30263) (cons 29784 30001) (cons 29588 29784) (cons 29430 29588) (cons 29111 29430) (cons 29073 29111) (cons 29044 29073) (cons 29030 29044) (cons 28784 29029) (cons 28651 28784) (cons 28578 28606) (cons 28481 28558) (cons 28374 28461) (cons 28291 28354) (cons 28135 28271) (cons 28027 28124) (cons 27580 28007) (cons 27525 27560) (cons 27470 27505) (cons 27394 27450) (cons 27368 28651) (cons 26886 27368) (cons 26496 26886) (cons 26005 26496) (cons 25748 26005) (cons 24908 25748) (cons 24660 24908) (cons 24258 24660) (cons 23643 24258) (cons 23318 23643) (cons 22923 23318) (cons 22494 22923) (cons 22263 22494) (cons 21735 22263) (cons 20632 21735) (cons 20182 20632) (cons 19630 20182) (cons 18248 19630) (cons 17937 18248) (cons 17884 17937) (cons 16657 17884) (cons 16485 16657) (cons 16372 16485) (cons 16337 16372) (cons 15999 16337) (cons 15444 15999) (cons 15306 15444) (cons 15288 15306) (cons 15153 15288) (cons 15034 15153) (cons 14698 15034) (cons 14557 14698) (cons 14232 14557) (cons 14203 14232) (cons 13936 14203) (cons 13851 13936) (cons 13631 13851) (cons 13587 13631) (cons 13555 13587) (cons 13231 13555) (cons 13085 13231) (cons 12391 13085) (cons 11998 12391) (cons 11511 11998) (cons 10871 11511) (cons 10553 10871) (cons 10472 10553) (cons 9233 10472) (cons 7902 9233) (cons 6842 7902) (cons 6597 6842) (cons 6559 6597) (cons 6530 6559) (cons 6516 6530) (cons 6498 6516) (cons 6340 6498) (cons 5992 6340) (cons 5943 5992) (cons 5772 5943) (cons 5315 5772) (cons 5181 5315) (cons 5129 5181) (cons 4920 5129) (cons 4261 4920) (cons 3682 4261) (cons 3021 3682) (cons 2883 3021) (cons 2540 2883) (cons 2342 2540) (cons 1184 2342) (cons 703 1184) (cons 665 703) (cons 636 665) (cons 622 636) (cons 377 622) (cons 1 377))))
  (repdyn-getpoint (ha_polyext projet_md_geststylechem-hach_re_offset) (ha_polyext projet_md_geststylechem-hach_re_offset2))
  (projet_md_geststylechem-bord_st_style (projet_md_geststylechem-hach_re_offset2 'projet_pa_axes))
)

(defun taldyn-list ()
  (axedyn-setrayext '(ls_reps ls_reps ls_rep ls_in in_max st_id))
)

(defun taldyn-get (en_rayon)
  (re_courant '(ls_reps ls_reps ls_rep ls_in in_max st_id) en_rayon)
)

(defun c:projet_pa_talus_oninitialize (/ gvar_3345 blkbib-getparententities sihpp-get in_lon0 re_cotechem)
  (entdel 'sivpano-supportswitch)
  (bo_lctabs sivpano-supportupdate blkbib-getparententities)
  (bo_lctabs sivpano-visi (eo_blkbase sihpp-get 2 2))
  (bo_lctabs sivpano-set in_lon0)
  (setq gvar_3345 (re_courant '(ls_reps ls_reps ls_rep ls_in in_max st_id) re_yinv))
  (setq blkbib-getparententities (in_param gvar_3345 "Repère"))
  (setq sihpp-get (in_param gvar_3345 'sihpp-contour))
  (setq in_lon0 (in_param gvar_3345 'ls_obj))
  (setq re_cotechem (in_param gvar_3345 'va_inters))
  gvar_2447
  (if (re_angle re_cotechem 1)
    (progn
      1
    )
    (progn
      0
    )
  )
  (st_num)
  (vlax-vla-object->ename sivpano-attrib polybib-vtxjoin)
  (polybib-absrem)
  (ls_som0)
)

(defun c:projet_pa_talus_re_pas_onsetfocus ()
  (ls_entnew sivpano-visi 0 255)
)

(defun c:projet_pa_talus_btn_reset_onclicked (/ gvar_3345)
  (fas-rtos3 '(ls_reps ls_reps ls_rep ls_in in_max st_id) re_yinv gvar_3345)
  (setq gvar_3345 sivpano-panominsert)
  (re_abs1 sivpano-panoinsert)
)

(defun c:projet_pa_talus_bt_select_onclicked ()
  (entdel 'sivpano-supminsert)
  (axe-set 'ocbib-isok sivpano-attrib)
)
