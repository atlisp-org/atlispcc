(cond
  ((or
     (string-equal "GstarCAD" @::cad-platform)
     (findfile "gcad.pgp"))
   (setq @::pgp-file "gcad.pgp")
    (@::set-locale "chs")
    (setq is-gstarcad T)
   (setq is-gcad T))
  ((or
     (wcmatch @::cad-platform "ZW*")
     (wcmatch @::cad-platform "SL*")
     (findfile "ZWCAD.pgp"))
    (setq @::pgp-file "ZWCAD.pgp")
    (@::set-locale "chs")
    (if (> (read (getvar "zrxvernum")) 2017)
      (setq @::*fasext* ".zelx"))
   (setq is-zwcad T))
  ((or
     (string-equal "bricscad" @::cad-platform)
     (string-equal "THCAD" @::cad-platform)
     (findfile "default.pgp"))
   (setq @::pgp-file "default.pgp")
   (setq is-bricscad T)
    (setq @::*fasext* ".des")
    (@::set-locale (strcase (getvar "locale") T)))
  ((string-equal "autocad" @::cad-platform)
   (setq @::pgp-file "acad.pgp")
   (setq is-autocad t)
    (cond
      ((= (getvar "syscodepage") "ANSI_936")
       (@::set-locale "chs"))
      ((= (getvar "syscodepage") "ANSI_950")
       (@::set-locale "cht"))
      (t (@::set-locale (strcase (getvar "locale") t)))))
   (t (@::set-locale "chs") (setq @::pgp-file "acad.pgp")))
